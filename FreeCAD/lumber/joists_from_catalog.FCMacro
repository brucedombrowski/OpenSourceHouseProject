# FreeCAD macro: build a joist assembly from the lumber_catalog.csv entries.
# Usage: Set the params below, then run the macro. It will create rim joists and interior joists
# spaced 16" OC (default) with a 3/4" offset for sheathing alignment. It pulls actual dimensions
# from the catalog row whose label matches `stock_label`.

import csv
import os
import FreeCAD as App
import Part

# -----------------------
# Parameters (inches)
# -----------------------
# Resolve catalog path robustly: first next to this macro, then parent project FreeCAD/lumber.
_macro_dir = os.path.dirname(__file__)
_project_root = os.path.dirname(os.path.dirname(_macro_dir))
catalog_candidates = [
    os.path.join(_macro_dir, "lumber_catalog.csv"),
    os.path.join(_project_root, "FreeCAD", "lumber", "lumber_catalog.csv"),
]
catalog_path = next((p for p in catalog_candidates if os.path.isfile(p)), None)
if not catalog_path:
    raise FileNotFoundError(f"Could not find lumber_catalog.csv. Checked: {catalog_candidates}")

stock_label = "2x12x192"     # Which catalog entry to use (e.g., 2x12x192)
module_length = 192.0        # Overall X dimension (outer edge to outer edge)
module_width  = 192.0        # Overall Y dimension
spacing_oc    = 16.0         # On-center spacing for interior joists (inches)
offset_first_center = 0.75   # Offset for first interior joist (inches) for sheathing alignment
make_pressure_treated = False  # If True, append "_PT" to label when looking up catalog

# -----------------------
# Helpers
# -----------------------
def inch(x): return x * 25.4

# Board orientation: X = length, Y = thickness, Z = depth (so boards stand upright)
def make_box(length, thickness, depth):
    return Part.makeBox(inch(length), inch(thickness), inch(depth))

def load_catalog(path):
    rows = []
    with open(path, newline="") as f:
        for row in csv.DictReader(f):
            rows.append(row)
    return rows

def find_stock(rows, label):
    for r in rows:
        if r.get("label") == label:
            return r
    return None

# -----------------------
# Main
# -----------------------
rows = load_catalog(catalog_path)
label_to_use = stock_label + "_PT" if make_pressure_treated else stock_label
row = find_stock(rows, label_to_use)
if not row:
    raise ValueError(f"Label '{label_to_use}' not found in catalog at {catalog_path}")

thick = float(row["actual_thickness_in"])
width = float(row["actual_width_in"])

doc = App.ActiveDocument or App.newDocument("FloorJoists_from_catalog")

def make_joist(name, y_pos, length=module_length, depth=width, thick=thick):
    # X = length, Y = thickness, Z = depth (standing upright)
    box = make_box(length, thick, depth)
    shape = doc.addObject("Part::Feature", name)
    shape.Shape = box
    # Place so joists run along X; distribute along Y (spacing_oc)
    shape.Placement.Base = App.Vector(inch(thick), inch(y_pos - thick/2.0), 0)
    # Attach metadata
    for key in ("sku_lowes", "url_lowes", "sku_hd", "url_hd"):
        if key not in shape.PropertiesList:
            shape.addProperty("App::PropertyString", key)
        shape.setPropertyStatus(key, ['Hidden'])
        shape.setPropertyStatus(key, [])
        shape.setExpression(key, None)
        shape.setPropertyStatus(key, [])
        shape.__setattr__(key, row.get(key, ""))
    shape.addProperty("App::PropertyString", "supplier").supplier = "lowes"
    shape.addProperty("App::PropertyString", "label").label = label_to_use
    return shape

# Rim joists at ends, running perpendicular to joists (along Y)
def make_rim(name, x_pos, length=module_width, depth=width, thick=thick):
    box = Part.makeBox(inch(thick), inch(length), inch(depth))  # X = thickness, Y = length, Z = depth
    shape = doc.addObject("Part::Feature", name)
    shape.Shape = box
    shape.Placement.Base = App.Vector(inch(x_pos - thick/2.0), 0, 0)
    for key in ("sku_lowes", "url_lowes", "sku_hd", "url_hd"):
        if key not in shape.PropertiesList:
            shape.addProperty("App::PropertyString", key)
        shape.__setattr__(key, row.get(key, ""))
    shape.addProperty("App::PropertyString", "supplier").supplier = "lowes"
    shape.addProperty("App::PropertyString", "label").label = label_to_use
    return shape

# Place rim joists with 3/4" offsets: left rim starts at +0.75, right rim ends at module_length + 0.75
left_rim  = make_rim("Rim_Left", 0.75, module_width)
right_rim = make_rim("Rim_Right", module_length - thick + 0.75, module_width)

# Interior joists
y = offset_first_center
idx = 1
while y < module_width - offset_first_center:
    make_joist(f"Joist_{idx}", y, module_length - 2 * thick)
    y += spacing_oc
    idx += 1
# Add a final joist near the far edge to close the box
make_joist(f"Joist_{idx}", module_width - offset_first_center, module_length - 2 * thick)

doc.recompute()
