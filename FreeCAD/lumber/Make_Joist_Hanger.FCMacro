# FreeCAD macro: generate a standalone joist hanger part using shared helpers.
# Purpose: quick inspection of hanger geometry/placement without joists.

import os
import sys
import FreeCAD as App
import Part
import importlib

# Ensure helper module is on path
_here = os.path.dirname(__file__)
if _here not in sys.path:
    sys.path.append(_here)

# Force-load lumber_common from this folder (avoid stale copies in other macro paths)
lc_path = os.path.join(_here, "lumber_common.py")
if "lumber_common" in sys.modules:
    del sys.modules["lumber_common"]
spec = importlib.util.spec_from_file_location("lumber_common", lc_path)
lumber_common = importlib.util.module_from_spec(spec)
spec.loader.exec_module(lumber_common)
make_hanger = lumber_common.make_hanger
inch = lumber_common.inch

# Parameters (adjust as needed)
hanger_label = "hanger_LU210"
hanger_thickness = 0.06     # ~16ga
hanger_height = 7.8125      # 7-13/16"
hanger_seat_depth = 2.0     # seat/back depth into rim
joist_thick = 1.5           # 2x thickness
joist_width = 11.25         # 2x12 depth
color = None                # None = keep per-part debug colors
direction = 1               # +1 = extends into +X (useful for left rim); -1 flips into -X
debug_components = True     # show colored sub-parts and names for review

doc = App.ActiveDocument or App.newDocument("Hanger_Test")

# Clear previous test hanger (group or subparts) to keep reruns clean
for obj in list(doc.Objects):
    if obj.Name == hanger_label or obj.Label == hanger_label or obj.Name.startswith(f"{hanger_label}_"):
        doc.removeObject(obj.Name)

# Create hanger at origin, centered on Y=0, seat below Z=0
h = make_hanger(
    doc,
    hanger_label,
    x_pos=0.0,
    y_center=0.0,
    thick=joist_thick,
    hanger_thickness=hanger_thickness,
    hanger_height=hanger_height,
    hanger_seat_depth=hanger_seat_depth,
    hanger_label=hanger_label,
    direction=direction,
    debug_components=debug_components,
    color=color,
)

doc.recompute()
try:
    App.Console.PrintMessage("[hanger test] created hanger debug parts\n")
except Exception:
    pass
