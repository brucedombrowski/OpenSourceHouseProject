# FreeCAD macro: Thin wrapper for creating a 16x8 joist assembly.
# All logic lives in joist_modules.py library.
# For Luke Dombrowski. Stay Alive.

import os
import sys
import FreeCAD as App

# Ensure library path is accessible
_here = os.path.dirname(__file__) if __file__ else os.getcwd()
if _here not in sys.path:
    sys.path.append(_here)

import lumber_common as lc
import parts

# Get active document or create new one
doc = App.ActiveDocument or App.newDocument("Joist_Module_16x8")

# Resolve catalog
catalog_path = lc.resolve_catalog([
    os.path.join(_here, "lumber_catalog.csv"),
    os.path.join(os.path.dirname(os.path.dirname(_here)), "FreeCAD", "lumber", "lumber_catalog.csv"),
])
catalog_rows = lc.load_catalog(catalog_path)

# Create assembly using library function
assembly = parts.create_joist_module_16x8(
    doc,
    catalog_rows,
    assembly_name="Joist_Module_16x8"
)

App.Console.PrintMessage("[Joist_Module_16x8] ✓ Assembly complete! For Luke. Stay Alive.\n")
