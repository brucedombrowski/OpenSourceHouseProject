# FreeCAD macro: export a simple BOM for lumber objects.
# It expects each object to have custom properties:
#   - label (stock label, e.g., 2x12x192 or 2x12x192_PT)
#   - supplier (e.g., lowes/hd)
#   - sku_lowes, url_lowes, sku_hd, url_hd (optional)
# It writes a CSV next to this macro (default: lumber_bom.csv).

import csv
import os
import math
import FreeCAD as App

doc = App.ActiveDocument
if not doc:
    raise RuntimeError("No active document.")

macro_dir = os.path.dirname(__file__)
out_path = os.path.join(macro_dir, "lumber_bom.csv")
catalog_path = os.path.join(macro_dir, "lumber_catalog.csv")

def load_catalog(path):
    if not os.path.isfile(path):
        return {}
    with open(path, newline="") as f:
        return {row["label"]: row for row in csv.DictReader(f)}

catalog = load_catalog(catalog_path)

def get(obj, attr, default=""):
    try:
        return getattr(obj, attr)
    except Exception:
        return default

bom = {}
for obj in doc.Objects:
    if "label" not in obj.PropertiesList:
        continue
    key = get(obj, "label", obj.Label)
    supplier = get(obj, "supplier", "lowes")
    entry = bom.setdefault(key, {
        "label": key,
        "qty": 0.0,
        "supplier": supplier,
        "sku_lowes": get(obj, "sku_lowes"),
        "url_lowes": get(obj, "url_lowes"),
        "sku_hd": get(obj, "sku_hd"),
        "url_hd": get(obj, "url_hd"),
    })

    # If catalog has dimensions, use area-based consolidation for panels.
    cat_row = catalog.get(key)
    nominal = cat_row.get("nominal", "") if cat_row else ""
    if nominal.startswith("4x8_panel"):
        try:
            panel_w = float(cat_row["actual_width_in"])
            panel_l = float(cat_row["length_in"])
            panel_area = panel_w * panel_l  # square inches
            bb = obj.Shape.BoundBox
            obj_area = (bb.XLength / 25.4) * (bb.YLength / 25.4)
            entry["qty"] += obj_area / panel_area
        except Exception:
            entry["qty"] += 1.0
    elif nominal.startswith("hardware_lu210"):
        # Hanger counted as 1 each
        entry["qty"] += 1.0
    else:
        entry["qty"] += 1.0

with open(out_path, "w", newline="") as f:
    writer = csv.DictWriter(f, fieldnames=["label", "qty", "supplier", "sku_lowes", "url_lowes", "sku_hd", "url_hd"])
    writer.writeheader()
    for row in bom.values():
        qty = row["qty"]
        # For panel-like items we may have fractional qty; round up to whole sheets
        qty_out = math.ceil(qty) if isinstance(qty, float) else qty
        row_out = dict(row)
        row_out["qty"] = qty_out
        writer.writerow(row_out)

App.Console.PrintMessage(f"BOM written to {out_path}\n")
