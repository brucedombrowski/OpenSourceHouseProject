# FreeCAD macro: Double 3x5 window wall (8' wide) — baseline frame (plates + end kings only).
# Iterative development will add jacks, header, sill, openings, and cripples to THIS file (no new step macros).
# Orientation: X = wall thickness (1.5"), Y = wall length (96"), Z = vertical.

import os
import sys
import importlib
import FreeCAD as App
import Part

_here = os.path.dirname(__file__)
if _here not in sys.path:
    sys.path.append(_here)

import lumber_common
importlib.reload(lumber_common)
from lumber_common import (
    ensure_macro_path,
    resolve_catalog,
    load_catalog,
    find_stock,
    attach_metadata,
    clear_group,
    inch,
)

ensure_macro_path()

# -----------------------
# Parameters (inches)
# -----------------------
wall_length = 96.0
plate_label = "2x4x96"
king_label = "2x4x104.625"
jack_label = "2x4x96"  # cut to height
jack_height = 80.0
header_label = "2x12x96"  # cut to header_length
header_length = 93.0  # 7'9" leaving 1.5" at each end inside kings
header_height = 11.25
ply_thickness = 0.5  # ripped sheet between header plies
ply_label = "plywood_0.5x4x8"
make_pressure_treated = False

_macro_dir = os.path.dirname(__file__)
_project_root = os.path.dirname(os.path.dirname(_macro_dir))
catalog_candidates = [
    os.path.join(_macro_dir, "lumber_catalog.csv"),
    os.path.join(_project_root, "FreeCAD", "lumber", "lumber_catalog.csv"),
]
catalog_path = resolve_catalog(catalog_candidates)

rows = load_catalog(catalog_path)

def catalog_row(label):
    key = label + "_PT" if make_pressure_treated else label
    row = find_stock(rows, key)
    if not row:
        raise ValueError(f"Label '{key}' not found in catalog at {catalog_path}")
    return row, key

plate_row, plate_key = catalog_row(plate_label)
king_row, king_key = catalog_row(king_label)
jack_row, jack_key = catalog_row(jack_label)
header_row, header_key = catalog_row(header_label)
ply_row, ply_key = catalog_row(ply_label)

plate_thick = float(plate_row["actual_thickness_in"])   # 1.5
plate_width = float(plate_row["actual_width_in"])       # 3.5
stud_thick = float(king_row["actual_thickness_in"])     # 1.5
stud_width = float(king_row["actual_width_in"])         # 3.5
stud_length = float(king_row["length_in"])              # 104.625
header_thick = float(header_row["actual_thickness_in"]) # 1.5
header_width = float(header_row["actual_width_in"])     # 11.25
ply_width = float(ply_row["actual_width_in"])

# Colors keyed by length/dimension
COLOR_PLATE = (1.0, 0.0, 0.0)   # red for 2x4x96 plates
COLOR_KING = (1.0, 1.0, 0.0)    # yellow for 2x4x104.625 kings
COLOR_JACK = (0.0, 1.0, 0.0)    # green for 80" jacks
COLOR_HEADER = (1.0, 0.5, 0.0)  # orange for 2x12 header plies
COLOR_PLY = (0.0, 0.6, 1.0)     # blue for 1/2" rip ply
COLOR_BLOCK = (0.0, 0.8, 0.8)   # teal for 11-7/8" header blocks
COLOR_BOTTOM_SHORT = (0.7, 0.2, 0.7)  # violet for short bottom studs
USE_DEBUG_COLORS = False  # set True to force fixed debug colors; otherwise use catalog-driven colors

doc = App.ActiveDocument or App.newDocument("Window_Wall_Double_3x5")

def apply_debug_color(obj, color):
    if not USE_DEBUG_COLORS or color is None:
        return
    try:
        obj.ViewObject.ShapeColor = color
    except Exception:
        pass


def make_plate(name, z_base):
    # Flat plate: X=3.5, Y=length, Z=1.5
    box = Part.makeBox(inch(stud_width), inch(wall_length), inch(plate_thick))
    obj = doc.addObject("Part::Feature", name)
    obj.Shape = box
    obj.Placement.Base = App.Vector(0, 0, inch(z_base))
    attach_metadata(obj, plate_row, plate_key, supplier="lowes")
    apply_debug_color(obj, COLOR_PLATE)
    return obj


created = []

# Plates
bottom_plate = make_plate("Plate_Bottom", 0.0)
top_plate = make_plate("Plate_Top", plate_thick + stud_length)
created.extend([bottom_plate, top_plate])

# End kings (rotated 90°: X=3.5, Y=1.5, Z=height)
def make_king(name, y_base):
    box = Part.makeBox(inch(stud_width), inch(stud_thick), inch(stud_length))
    obj = doc.addObject("Part::Feature", name)
    obj.Shape = box
    obj.Placement.Base = App.Vector(0, inch(y_base), inch(plate_thick))
    attach_metadata(obj, king_row, king_key, supplier="lowes")
    apply_debug_color(obj, COLOR_KING)
    return obj

created.append(make_king("King_Left", 0.0))
created.append(make_king("King_Right", wall_length - stud_thick))

# Jacks (80") inside kings
def make_jack(name, y_base):
    box = Part.makeBox(inch(stud_width), inch(stud_thick), inch(jack_height))
    obj = doc.addObject("Part::Feature", name)
    obj.Shape = box
    obj.Placement.Base = App.Vector(0, inch(y_base), inch(plate_thick))
    attach_metadata(obj, jack_row, jack_key, supplier="lowes")
    try:
        obj.addProperty("App::PropertyString", "cut_length_in").cut_length_in = f"{jack_height}"
    except Exception:
        pass
    apply_debug_color(obj, COLOR_JACK)
    return obj

created.append(make_jack("Jack_Left", stud_thick))  # sits right next to left king
created.append(make_jack("Jack_Right", wall_length - (2 * stud_thick)))  # sits just inside right king

# Built-up header: 2x12 + 0.5" ply + 2x12 (total 3.5"), sitting on jacks
header_start_y = stud_thick  # 1.5" in from left
header_z_base = plate_thick + jack_height
cap_plate_z = header_z_base + header_height

def make_header(name, y_base, thickness, color, x_base=0.0):
    box = Part.makeBox(inch(thickness), inch(header_length), inch(header_height))
    obj = doc.addObject("Part::Feature", name)
    obj.Shape = box
    obj.Placement.Base = App.Vector(inch(x_base), inch(y_base), inch(header_z_base))
    attach_metadata(obj, header_row, header_key, supplier="lowes")
    try:
        obj.addProperty("App::PropertyString", "cut_length_in").cut_length_in = f"{header_length}"
    except Exception:
        pass
    apply_debug_color(obj, color)
    return obj

created.append(make_header("Header_2x12_A", header_start_y, header_thick, COLOR_HEADER, x_base=0.0))

# 1/2" rip layer
ply = Part.makeBox(inch(ply_thickness), inch(header_length), inch(header_height))
ply_obj = doc.addObject("Part::Feature", "Header_Ply_0p5")
ply_obj.Shape = ply
ply_obj.Placement.Base = App.Vector(inch(header_thick), inch(header_start_y), inch(header_z_base))
attach_metadata(ply_obj, ply_row, ply_key, supplier="lowes")
try:
    ply_obj.addProperty("App::PropertyString", "cut_length_in").cut_length_in = f"{header_length}"
except Exception:
    pass
apply_debug_color(ply_obj, COLOR_PLY)
created.append(ply_obj)

created.append(make_header("Header_2x12_B", header_start_y, header_thick, COLOR_HEADER, x_base=header_thick + ply_thickness))

# Cap plate atop header (2x4x93)
cap_plate = Part.makeBox(inch(stud_width), inch(header_length), inch(plate_thick))
cap_plate_obj = doc.addObject("Part::Feature", "Header_Cap_Plate")
cap_plate_obj.Shape = cap_plate
cap_plate_obj.Placement.Base = App.Vector(0, inch(header_start_y), inch(cap_plate_z))
attach_metadata(cap_plate_obj, plate_row, plate_key, supplier="lowes")
try:
    cap_plate_obj.addProperty("App::PropertyString", "cut_length_in").cut_length_in = f"{header_length}"
except Exception:
    pass
apply_debug_color(cap_plate_obj, COLOR_PLATE)
created.append(cap_plate_obj)

# Short blocks (11-7/8") on 16" OC atop header
block_height = 11.875
def make_block(name, y_base):
    box = Part.makeBox(inch(stud_width), inch(stud_thick), inch(block_height))
    obj = doc.addObject("Part::Feature", name)
    obj.Shape = box
    # Shift blocks up 1.5" (plate thickness) above header top
    obj.Placement.Base = App.Vector(0, inch(y_base), inch(header_z_base + header_height + plate_thick))
    attach_metadata(obj, plate_row, plate_key, supplier="lowes")  # cut from 2x4x96 stock
    try:
        obj.addProperty("App::PropertyString", "cut_length_in").cut_length_in = f"{block_height}"
    except Exception:
        pass
    apply_debug_color(obj, COLOR_BLOCK)
    return obj

blocks_added = 0
center = header_start_y + stud_thick / 2.0
while blocks_added < 7 and center <= header_start_y + header_length - (stud_thick / 2.0) + 1e-6:
    y_base = center - (stud_thick / 2.0)
    created.append(make_block(f"Header_Block_{blocks_added+1}", y_base))
    blocks_added += 1
    center += 16.0

# Short studs (15.5") on bottom plate, 16" OC, spanning between jack faces
short_height = 15.5
def make_short(name, y_base):
    box = Part.makeBox(inch(stud_width), inch(stud_thick), inch(short_height))
    obj = doc.addObject("Part::Feature", name)
    obj.Shape = box
    obj.Placement.Base = App.Vector(0, inch(y_base), inch(plate_thick))
    attach_metadata(obj, plate_row, plate_key, supplier="lowes")  # cut from 2x4x96 stock
    try:
        obj.addProperty("App::PropertyString", "cut_length_in").cut_length_in = f"{short_height}"
    except Exception:
        pass
    apply_debug_color(obj, COLOR_BOTTOM_SHORT)
    return obj

short_added = 0
short_base = stud_thick  # start flush to left jack face
while short_added < 7:
    y_pos = short_base
    if short_added == 0:  # shift first stud +1.5" in Y
        y_pos += 1.5
    if short_added == 6:  # shift the 7th stud -6" in Y
        y_pos -= 6.0
    created.append(make_short(f"Short_Bottom_{short_added+1}", y_pos))
    short_added += 1
    short_base += 16.0

# 90" 2x4 atop the short studs (cap for lower opening)
cap_bottom_length = 90.0
cap_bottom_start_y = header_start_y + (header_length - cap_bottom_length) / 2.0  # center between jacks
cap_bottom = Part.makeBox(inch(stud_width), inch(cap_bottom_length), inch(plate_thick))
cap_bottom_obj = doc.addObject("Part::Feature", "Bottom_Cap_90")
cap_bottom_obj.Shape = cap_bottom
cap_bottom_obj.Placement.Base = App.Vector(0, inch(cap_bottom_start_y), inch(plate_thick + short_height))
attach_metadata(cap_bottom_obj, plate_row, plate_key, supplier="lowes")
try:
    cap_bottom_obj.addProperty("App::PropertyString", "cut_length_in").cut_length_in = f"{cap_bottom_length}"
except Exception:
    pass
apply_debug_color(cap_bottom_obj, COLOR_PLATE)
created.append(cap_bottom_obj)

# Second 2x4x90 cap atop the first cap
cap_second_z = plate_thick + short_height + plate_thick  # top of first cap
cap_second = Part.makeBox(inch(stud_width), inch(cap_bottom_length), inch(plate_thick))
cap_second_obj = doc.addObject("Part::Feature", "Bottom_Cap_90_2")
cap_second_obj.Shape = cap_second
cap_second_obj.Placement.Base = App.Vector(0, inch(cap_bottom_start_y), inch(cap_second_z))
attach_metadata(cap_second_obj, plate_row, plate_key, supplier="lowes")
try:
    cap_second_obj.addProperty("App::PropertyString", "cut_length_in").cut_length_in = f"{cap_bottom_length}"
except Exception:
    pass
apply_debug_color(cap_second_obj, COLOR_PLATE)
created.append(cap_second_obj)

# Six 60" studs on top of second cap to form two 36" openings
stud60_height = 60.0
stud60_z_base = cap_second_z + plate_thick  # sit on second cap
# Layout per spec:
# stud2 is 36" from stud1; stud3 adjacent to stud2; 9" gap to stud4; stud5 adjacent to stud4; stud6 is 36" from stud5 and aligns to jack.
stud60_positions = []
y1 = cap_bottom_start_y  # left face aligned to right face of left jack
stud60_positions.append(y1)
y2 = y1 + 36.0
stud60_positions.append(y2)
y3 = y2 + stud_thick
stud60_positions.append(y3)
y4 = y3 + 15.0  # widened gap to land stud6 near jack face
stud60_positions.append(y4)
y5 = y4 + stud_thick
stud60_positions.append(y5)
y6 = y5 + 36.0 - 1.5  # adjust -1.5" in Y
stud60_positions.append(y6)

def make_stud60(name, y_base):
    box = Part.makeBox(inch(stud_width), inch(stud_thick), inch(stud60_height))
    obj = doc.addObject("Part::Feature", name)
    obj.Shape = box
    obj.Placement.Base = App.Vector(0, inch(y_base), inch(stud60_z_base))
    attach_metadata(obj, plate_row, plate_key, supplier="lowes")  # cut from 2x4x96 stock
    try:
        obj.addProperty("App::PropertyString", "cut_length_in").cut_length_in = f"{stud60_height}"
    except Exception:
        pass
    apply_debug_color(obj, COLOR_KING)
    return obj

for idx, y_base in enumerate(stud60_positions, start=1):
    created.append(make_stud60(f"Stud60_{idx}", y_base))

# Top 2x4x90 cap over 60" studs
cap_top_z = stud60_z_base + stud60_height
cap_top = Part.makeBox(inch(stud_width), inch(cap_bottom_length), inch(plate_thick))
cap_top_obj = doc.addObject("Part::Feature", "Bottom_Cap_90_3")
cap_top_obj.Shape = cap_top
cap_top_obj.Placement.Base = App.Vector(0, inch(cap_bottom_start_y), inch(cap_top_z))
attach_metadata(cap_top_obj, plate_row, plate_key, supplier="lowes")
try:
    cap_top_obj.addProperty("App::PropertyString", "cut_length_in").cut_length_in = f"{cap_bottom_length}"
except Exception:
    pass
apply_debug_color(cap_top_obj, COLOR_PLATE)
created.append(cap_top_obj)

group_name = "Window_Wall_Double_3x5"
clear_group(doc, group_name)
group = doc.addObject("App::DocumentObjectGroup", group_name)
group.Label = group_name
for obj in created:
    group.addObject(obj)
group.Group = created

App.Console.PrintMessage(
    f"[Window Double 3x5] Built: plates (2), end kings (2), jacks (2), built-up header (3 plies), cap plate, header blocks (7), wall length {wall_length}\".\n"
)
doc.recompute()
