# -*- coding: utf-8 -*-
"""Build 950 Surf Beach House - Refactored Version

Construction-grade parametric model for 950 Surf Ave beach house.

Architecture:
    - Foundation: 30 pilings (5x6 grid) with double beams and blocking
    - Floor: Two 16x16 joist modules with sheathing
    - Walls: 2x4 framing with window/door openings
    - Stairs: Interior/exterior access
    - Second Floor: Mirrors first floor layout
    - Roof: Gable + shed configurations

Build Sequence (realistic construction order):
    1. Lot survey lines
    2. Foundation (piles, beams, blocking)
    3. Deck joists (installed with first floor framing)
    4. First floor joists + sheathing
    5. First floor walls
    6. Deck surface (boards installed before second floor for safe work platform)
    7. Second floor joists + sheathing
    8. Second floor walls
    9. Stairs
    10. Roofing

    NOTE: Build order follows realistic construction sequence. Deck boards are
    installed BEFORE second floor framing to provide a safe walking surface for
    workers during upper-level construction.

Usage:
    Run this macro in FreeCAD. It will generate the complete house model
    and export BOM to beach_bom.csv.

Author: OpenSourceHouseProject
Dedication: For Luke Dombrowski. Stay Alive.
"""

import importlib
import os
import sys

import Part

import FreeCAD as App

# Import BeachHouse helpers and config
# Use absolute paths to work when macro is copied to builds/ folder
_this_file = __file__ if __file__ else os.getcwd()
_macro_location = os.path.dirname(os.path.abspath(_this_file))

# If this macro is in builds/, navigate to DesignHouse root
# Structure: FreeCAD/DesignHouse/builds/macro.FCMacro
# We need to get to: FreeCAD/DesignHouse/
if os.path.basename(_macro_location) == "builds":
    # Go up from builds/ -> DesignHouse/
    _design_house_root = os.path.dirname(_macro_location)
else:
    # Macro is in DesignHouse/ directly (template location)
    _design_house_root = _macro_location

_macros_dir = os.path.join(_design_house_root, "macros")

if _macros_dir not in sys.path:
    sys.path.append(_macros_dir)
if _design_house_root not in sys.path:
    sys.path.append(_design_house_root)

try:
    import beach_common as bc
    import beach_elevator as be
    import beam_assemblies as ba
    import pile_connections as pc
    import septic_utilities as su
    BEACH_COMMON_AVAILABLE = True
except ImportError:
    App.Console.PrintError(
        "[Build_950Surf] Required modules not found; cannot proceed.\n"
        "Ensure all helper modules exist in macros/ directory:\n"
        "  - beach_common.py, beam_assemblies.py, septic_utilities.py\n"
        "  - beach_elevator.py, pile_connections.py\n"
    )
    raise

# Import design configuration
# BEACH_CONFIG env var MUST point to a config file (e.g., "ExampleBeachHouse/config.py")
beach_config_path = os.environ.get("BEACH_CONFIG", "")

if not beach_config_path:
    App.Console.PrintError("[BeachHouse] ERROR: BEACH_CONFIG environment variable not set.\n")
    App.Console.PrintError("[BeachHouse] Please set BEACH_CONFIG to your config file path.\n")
    App.Console.PrintError("[BeachHouse] Example: export BEACH_CONFIG=ExampleBeachHouse/config.py\n")
    raise RuntimeError("BEACH_CONFIG environment variable not set")

# Load config from specified path
try:
    import importlib.util
    spec = importlib.util.spec_from_file_location("beach_config", beach_config_path)
    beach_config = importlib.util.module_from_spec(spec)
    spec.loader.exec_module(beach_config)
    LOT = beach_config.LOT
    FOUNDATION = beach_config.FOUNDATION
    FIRST_FLOOR = beach_config.FIRST_FLOOR
    SECOND_FLOOR = beach_config.SECOND_FLOOR
    SEPTIC_SYSTEM = beach_config.SEPTIC_SYSTEM
    UTILITIES = beach_config.UTILITIES
    DECKS = beach_config.DECKS
    DRIVEWAY = beach_config.DRIVEWAY
    ELEVATOR = beach_config.ELEVATOR
    STAIRS = beach_config.STAIRS
    WALLS = beach_config.WALLS
    BUILD = beach_config.BUILD
    App.Console.PrintMessage(f"[BeachHouse] Loaded design configuration from {beach_config_path}\n")
except Exception as e:
    App.Console.PrintError(f"[BeachHouse] Failed to load config from {beach_config_path}: {e}\n")
    raise

# ============================================================
# EXTRACT PARAMETERS FROM CONFIG
# ============================================================

# Lot geometry
lot_x_ft = LOT["width_ft"]
lot_y_ft = LOT["depth_ft"]
front_setback_ft = LOT["front_setback_ft"]  # South side
left_setback_ft = LOT["left_setback_ft"]    # West side
right_setback_ft = LOT["right_setback_ft"]  # East side
rear_setback_ft = LOT["rear_setback_ft"]    # North side

# Foundation
pile_label = "12x12x40_piling_PT"
pile_length_ft = FOUNDATION["pile_length_ft"]
embed_depth_ft = FOUNDATION["pile_embed_depth_ft"]
above_grade_ft = pile_length_ft - embed_depth_ft  # CALCULATED: top of foundation above grade
pile_base_z_in = -embed_depth_ft * 12.0

# Pile grid
num_piles_x = FOUNDATION["pile_grid_x"]
num_piles_y = FOUNDATION["pile_grid_y"]
y_spacing_ft = FOUNDATION["pile_spacing_y_ft"]

# Pile thickness (for face alignment calculations)
pile_thickness_ft = FOUNDATION["pile_actual_size_in"] / 12.0
pile_half_thickness_ft = pile_thickness_ft / 2.0

# X positions: outside faces of outside columns align with setback lines
# West pile: west face at left setback line, so center = left_setback + half_thickness
# East pile: east face at right setback line, so center = lot_width - right_setback - half_thickness
# Interior piles: evenly spaced between west and east piles
west_pile_center_x_ft = left_setback_ft + pile_half_thickness_ft
east_pile_center_x_ft = lot_x_ft - right_setback_ft - pile_half_thickness_ft
if num_piles_x > 1:
    x_spacing_ft = (east_pile_center_x_ft - west_pile_center_x_ft) / (num_piles_x - 1)
else:
    x_spacing_ft = 0.0
x_positions_ft = [west_pile_center_x_ft + i * x_spacing_ft for i in range(num_piles_x)]

# Y positions: front pile face at front setback
# Shift center by half pile thickness so face aligns with setback
start_y_ft = front_setback_ft + pile_half_thickness_ft
y_positions_ft = [start_y_ft + i * y_spacing_ft for i in range(num_piles_y)]

# Beam parameters (double-beam assemblies running along Y)
beam_label = "beam_2x12x192_PT"
beam_row_step = FOUNDATION["beam_row_interval"]
beam_gap_in = FOUNDATION["beam_gap_in"]

# Blocking parameters (lateral support per IRC R502.7)
blocking_offsets_ft = FOUNDATION["blocking_offsets_ft"]

# Mid-span boards (additional support between pile rows)
mid_board_label = "beam_2x12x96_PT"
mid_board_offset_L_in = FOUNDATION["mid_board_offset_left_in"]
mid_board_offset_R_in = FOUNDATION["mid_board_offset_right_in"]

# Joist module parameters (from config)
module_x_ft = 16.0
module_y_ft = 16.0
module_joist_label = "joist_2x12_PT"
module_first_spacing_in = FIRST_FLOOR["joist_first_spacing_in"]
module_joist_spacing_in = FIRST_FLOOR["joist_spacing_oc_in"]
module_left_x_ft = lot_x_ft / 2.0  # Align to lot centerline
module_front_y_ft = front_setback_ft
module_base_z_ft = above_grade_ft

# Front deck positioning (derived from config - used by elevator and deck modules)
front_deck_rim_offset_ft = DECKS["front_deck_rim_offset_in"] / 12.0
front_deck_depth_ft = DECKS["front_deck_depth_ft"]  # 12' for 16x12 modules
front_deck_y_ft = front_setback_ft + y_spacing_ft - front_deck_depth_ft - front_deck_rim_offset_ft

# Sheathing parameters
sheathing_thick_in = FIRST_FLOOR["sheathing_thickness_in"]
sheathing_label = FIRST_FLOOR["sheathing_stock"]

# Hanger parameters (from config)
hanger_label = "hanger_LU210"
hanger_thickness_in = FIRST_FLOOR["hanger_thickness_in"]
hanger_height_in = FIRST_FLOOR["hanger_height_in"]
hanger_seat_depth_in = FIRST_FLOOR["hanger_seat_depth_in"]
hanger_color = None

# ============================================================
# CATALOG LOADING
# ============================================================

App.Console.PrintMessage("[Build_950Surf] Loading catalogs...\n")
catalog = bc.load_beach_catalog()
bc.print_catalog_summary(catalog)

# ============================================================
# DOCUMENT SETUP
# ============================================================

doc = App.newDocument("950Surf")
App.Console.PrintMessage("[Build_950Surf] Created document: 950Surf\n")

# ============================================================
# SECTION 1: LOT SURVEY (Boundary + Buildable Area + Origin)
# ============================================================

def create_lot_survey(doc, lot_x_ft, lot_y_ft, front_setback_ft, left_setback_ft, right_setback_ft, rear_setback_ft):
    """Create lot survey boundary, buildable area, and origin marker.

    Construction Notes:
        - Lot boundary shows property lines (legal survey)
        - Buildable area shows zoning envelope (setbacks applied)
        - Origin marker at (0,0) for reference

    Args:
        doc: FreeCAD document
        lot_x_ft: Lot width in feet (X, east-west)
        lot_y_ft: Lot depth in feet (Y, north-south)
        front_setback_ft: Front (south) setback per zoning
        left_setback_ft: Left (west) setback per zoning
        right_setback_ft: Right (east) setback per zoning
        rear_setback_ft: Rear (north) setback per zoning

    Returns:
        lot_grp: DocumentObjectGroup containing lot geometry
    """
    App.Console.PrintMessage("[Build_950Surf] Creating lot survey...\n")

    # Lot boundary (property lines)
    lot_pts = [
        App.Vector(0, 0, 0),
        App.Vector(bc.ft(lot_x_ft), 0, 0),
        App.Vector(bc.ft(lot_x_ft), bc.ft(lot_y_ft), 0),
        App.Vector(0, bc.ft(lot_y_ft), 0),
        App.Vector(0, 0, 0),  # Close polygon
    ]
    lot_wire = Part.makePolygon(lot_pts)
    lot_obj = doc.addObject("Part::Feature", "Lot_Boundary")
    lot_obj.Shape = lot_wire

    # Buildable area (zoning envelope)
    buildable_pts = [
        App.Vector(bc.ft(left_setback_ft), bc.ft(front_setback_ft), 0),
        App.Vector(bc.ft(lot_x_ft - right_setback_ft), bc.ft(front_setback_ft), 0),
        App.Vector(bc.ft(lot_x_ft - right_setback_ft), bc.ft(lot_y_ft - rear_setback_ft), 0),
        App.Vector(bc.ft(left_setback_ft), bc.ft(lot_y_ft - rear_setback_ft), 0),
        App.Vector(bc.ft(left_setback_ft), bc.ft(front_setback_ft), 0),
    ]
    buildable_wire = Part.makePolygon(buildable_pts)
    buildable_obj = doc.addObject("Part::Feature", "Buildable_Area")
    buildable_obj.Shape = buildable_wire

    # Origin marker (cross at 0,0)
    marker_size_ft = LOT.get("origin_marker_size_ft", 1.0)
    cross_lines = [
        Part.makeLine(App.Vector(-bc.ft(marker_size_ft), 0, 0), App.Vector(bc.ft(marker_size_ft), 0, 0)),
        Part.makeLine(App.Vector(0, -bc.ft(marker_size_ft), 0), App.Vector(0, bc.ft(marker_size_ft), 0)),
    ]
    cross_obj = doc.addObject("Part::Feature", "Origin_Marker")
    cross_obj.Shape = Part.Compound(cross_lines)

    # Group lot objects
    lot_grp = bc.create_group(doc, "Lot")
    bc.add_to_group(lot_grp, [lot_obj, buildable_obj, cross_obj])

    App.Console.PrintMessage("[Build_950Surf] Lot survey complete.\n")
    return lot_grp

# Create lot survey
lot_grp = create_lot_survey(doc, lot_x_ft, lot_y_ft, front_setback_ft, left_setback_ft, right_setback_ft, rear_setback_ft)

# ============================================================
# SECTION 2: SEPTIC SYSTEM (if enabled)
# ============================================================

if BUILD.get("include_septic_system", False):
    App.Console.PrintMessage("[Build_950Surf] === SEPTIC SYSTEM ===\n")
    # Calculate leach field Y start from pile positions (no hardcoded values)
    # Leach field must start north of the last pile row with clearance
    last_pile_y_ft = y_positions_ft[-1]  # Last pile center Y
    last_pile_north_face_ft = last_pile_y_ft + pile_half_thickness_ft
    leach_field_clearance_ft = 2.0  # 2' clearance from pile for access/maintenance
    calculated_leach_y_start_ft = last_pile_north_face_ft + leach_field_clearance_ft

    # Calculate drain stub-up position from pile positions (no hardcoded values)
    # Stub-up at east face of pile [3,4] (0-based indices: column 4, row 5 in 1-based)
    # This aligns with the stair module at Floor_Middle_Right_16x8
    drain_stub_pile_col = 3  # Pile column index (0-based)
    drain_stub_pile_row = 4  # Pile row index (0-based)
    drain_stub_pile_x_ft = x_positions_ft[drain_stub_pile_col]
    drain_stub_pile_y_ft = y_positions_ft[drain_stub_pile_row]
    drain_pipe_diameter_in = SEPTIC_SYSTEM.get("drain_line_diameter_in", 4.0)
    # East face of pile: pile center X + pile half thickness
    # Pipe center at east face: east face X + pipe radius
    drain_stub_east_face_ft = drain_stub_pile_x_ft + pile_half_thickness_ft
    drain_stub_x_ft = drain_stub_east_face_ft + (drain_pipe_diameter_in / 2.0) / 12.0

    # Create septic config with calculated positions
    septic_config = dict(SEPTIC_SYSTEM)
    septic_config["leach_field_y_start_ft"] = calculated_leach_y_start_ft
    septic_config["stub_up_x_ft"] = drain_stub_x_ft
    septic_config["stub_up_y_ft"] = drain_stub_pile_y_ft
    App.Console.PrintMessage(f"[Build_950Surf]   Leach field Y start: {calculated_leach_y_start_ft:.2f}' (2' north of last pile at Y={last_pile_y_ft:.2f}')\n")
    App.Console.PrintMessage(f"[Build_950Surf]   Drain stub-up at pile [{drain_stub_pile_col},{drain_stub_pile_row}] east face: X={drain_stub_x_ft:.3f}', Y={drain_stub_pile_y_ft:.5f}'\n")

    septic_grp = su.create_septic_system(doc, septic_config)
else:
    App.Console.PrintMessage("[Build_950Surf] Septic system skipped (disabled in BUILD config)\n")

# ============================================================
# SECTION 3: FOUNDATION (Piles, Beams, Blocking, Mid-Boards)
# ============================================================

def create_foundation(doc, catalog, params):
    """Build pile foundation with LVL beam assemblies.

    Construction Sequence:
        1. Install pilings (35 ea, 12x12x40 PT, embedded 20' below grade)
        2. Install LVL beam assemblies (1.75"xdepthx20' 2-ply, centered on piles)
        3. Notch piles for beam seats (single 3.5" wide notch per pile)

    Design Rationale:
        - Pile grid: 5x7 = 35 piles @ 10' OC (efficient use of 20' LVL stock)
        - Embed depth: 20' below grade (local code + storm surge + safety factor)
        - Above grade: 20' (elevated above max flood elevation per FEMA)
        - LVL beams: 2-ply laminated (3.5" total width) centered on piles
        - Three 20' segments per girder: rows 1-3, 3-5, 5-7
        - Single notch per pile: 3.5" wide x depth deep

    Args:
        doc: FreeCAD document
        catalog: Catalog rows from beach_common
        params (dict): Foundation parameters with keys:
            - pile_label, x_positions_ft, y_positions_ft, pile_base_z_in, pile_height_in
            - lvl_label (e.g., "lvl_1.75x11.875x240")

    Returns:
        foundation_grp: DocumentObjectGroup with subgroups:
            - Piles (35 ea)
            - LVL_Beam_Assemblies (15 assemblies: 5 girders x 3 segments each)

    Raises:
        ValueError: If pile_label or lvl_label not found in catalog
    """
    App.Console.PrintMessage("[Build_950Surf] Building foundation with LVL beams...\n")

    # Lookup catalog entries (fail-fast if not found)
    pile_row = bc.find_stock(catalog, params["pile_label"])
    lvl_row = bc.find_stock(catalog, params["lvl_label"])

    # Extract dimensions from catalog
    pile_width_in = float(pile_row["actual_width_in"])
    pile_thick_in = float(pile_row["actual_thickness_in"])
    pile_len_in = float(pile_row["length_in"])

    lvl_ply_thick_in = float(lvl_row["actual_thickness_in"])  # 1.75"
    lvl_depth_in = float(lvl_row["actual_width_in"])  # Variable (11.875", 24", etc.)
    lvl_total_width_in = lvl_ply_thick_in * 2  # 3.5" (2 plies)

    # Calculate Z positions
    pile_height_in = params["pile_height_in"]
    beam_top_z_in = params["pile_base_z_in"] + pile_len_in
    beam_base_z_in = beam_top_z_in - lvl_depth_in

    # === CREATE PILES ===
    App.Console.PrintMessage("[Build_950Surf]   Creating piles...\n")
    pile_objs = []
    for xi_ft in params["x_positions_ft"]:
        for yi_ft in params["y_positions_ft"]:
            name = f"Pile_{int(xi_ft)}_{int(yi_ft)}"
            pile = bc.make_pile(
                doc, catalog, params["pile_label"], name,
                xi_ft, yi_ft, params["pile_base_z_in"], pile_height_in
            )
            pile_objs.append(pile)

    App.Console.PrintMessage(f"[Build_950Surf]   Created {len(pile_objs)} piles.\n")

    # === CREATE LVL BEAM ASSEMBLIES ===
    App.Console.PrintMessage("[Build_950Surf]   Creating LVL beam assemblies (3 segments per girder)...\n")
    lvl_assemblies = []

    # Validate pile count (must be 7 for standard 3-segment pattern)
    if len(params["y_positions_ft"]) != 7:
        raise ValueError(
            f"LVL beam system requires 7 pile rows, got {len(params['y_positions_ft'])}"
        )

    # Create 3 LVL segments for each girder line (5 girders x 3 segments = 15 assemblies)
    # Determine LVL placement side: west girders on west face, east girders on east face
    middle_x_ft = (params["x_positions_ft"][0] + params["x_positions_ft"][-1]) / 2.0

    for girder_idx, xi_ft in enumerate(params["x_positions_ft"]):
        # West girders (X < middle): place LVL on west face of pile
        # East girders (X > middle): place LVL on east face of pile
        # Middle girder (X = middle): use west face for simplicity
        lvl_side = "west" if xi_ft <= middle_x_ft else "east"

        assemblies = ba.create_lvl_beam_segments_for_girder(
            doc,
            catalog,
            x_girder_ft=xi_ft,
            y_pile_positions_ft=params["y_positions_ft"],
            z_base_in=beam_base_z_in,
            lvl_label=params["lvl_label"],
            girder_idx=girder_idx,
            side=lvl_side,
        )
        lvl_assemblies.extend(assemblies)

    App.Console.PrintMessage(f"[Build_950Surf]   Created {len(lvl_assemblies)} LVL beam assemblies.\n")

    # === PILE-TO-BEAM CONNECTIONS (notches + bolts) ===
    # Delegate to pile_connections module for notching and bolt creation
    # This handles:
    #   - Notch type detection (endpoint corner vs middle/boundary full-width)
    #   - Segment boundary detection (where two LVL segments meet)
    #   - Threaded rod placement with proper Y positioning (centered on notched half)
    #   - Rod X positioning (centered on pile with protrusion on both ends)
    #   - Rod Z positioning (equal thirds: 1/3 and 2/3 of beam depth)
    notch_count, notched_piles, anchor_bolts_created = pc.create_all_pile_connections(
        doc,
        catalog,
        pile_objs,
        lvl_assemblies,
        pile_width_in,
        pile_thick_in,
        lvl_total_width_in,
        lvl_depth_in,
        beam_base_z_in,
    )

    # === GROUP FOUNDATION ===
    foundation_grp = bc.create_group(doc, "Foundation")
    piles_grp = bc.create_group(doc, "Piles")
    lvl_beam_assemblies_grp = bc.create_group(doc, "LVL_Beam_Assemblies")
    anchor_bolts_grp = bc.create_group(doc, "Anchor_Bolts")

    bc.add_to_group(piles_grp, pile_objs)
    bc.add_to_group(lvl_beam_assemblies_grp, lvl_assemblies)
    bc.add_to_group(anchor_bolts_grp, anchor_bolts_created)
    bc.add_to_group(foundation_grp, [piles_grp, lvl_beam_assemblies_grp, anchor_bolts_grp])

    App.Console.PrintMessage("[Build_950Surf] Foundation complete.\n")
    return foundation_grp

# Create foundation
foundation_params = {
    "pile_label": pile_label,
    "x_positions_ft": x_positions_ft,
    "y_positions_ft": y_positions_ft,
    "pile_base_z_in": pile_base_z_in,
    "pile_height_in": above_grade_ft * 12.0 - pile_base_z_in,
    "lvl_label": FOUNDATION.get("lvl_label", "lvl_1.75x11.875x240"),  # LVL beam catalog key
}

foundation_grp = create_foundation(doc, catalog, foundation_params)

# ============================================================
# SECTION 4: UTILITIES AND CONCRETE SLAB (if enabled)
# ============================================================

if BUILD.get("include_concrete_slab", BUILD.get("include_utilities", False)):
    App.Console.PrintMessage("[Build_950Surf] === CONCRETE SLAB ===\n")
    # Pass pile positions for slab cutouts (use actual pile size, not nominal)
    pile_positions_ft = [(x, y) for x in x_positions_ft for y in y_positions_ft]

    # Calculate slab dimensions from pile positions (no hardcoded values)
    # Slab covers pile area but MUST stay within setback lines
    # Pile outer faces already align with setback lines, so slab edge = setback line
    # West edge: left_setback_ft (pile west face aligns here)
    # East edge: lot_x_ft - right_setback_ft (pile east face aligns here)
    # South edge: front_setback_ft (pile south face aligns here)
    # North edge: last pile north face + margin (but no setback issue here - rear is for building only)
    slab_margin_north_ft = 0.5  # 6" margin on north side only (no setback constraint)
    calculated_slab_x_start = left_setback_ft  # West edge at left setback line
    calculated_slab_x_end = lot_x_ft - right_setback_ft  # East edge at right setback line
    calculated_slab_y_start = front_setback_ft  # South edge at front setback line
    calculated_slab_y_end = y_positions_ft[-1] + pile_half_thickness_ft + slab_margin_north_ft  # North edge with margin
    calculated_slab_width = calculated_slab_x_end - calculated_slab_x_start
    calculated_slab_depth = calculated_slab_y_end - calculated_slab_y_start

    # Override slab dimensions in utilities config
    utilities_slab_config = dict(UTILITIES)
    utilities_slab_config["slab_x_start_ft"] = calculated_slab_x_start
    utilities_slab_config["slab_y_start_ft"] = calculated_slab_y_start
    utilities_slab_config["slab_width_ft"] = calculated_slab_width
    utilities_slab_config["slab_depth_ft"] = calculated_slab_depth
    App.Console.PrintMessage(f"[Build_950Surf]   Slab within setbacks: X={calculated_slab_x_start:.2f}'-{calculated_slab_x_end:.2f}', Y={calculated_slab_y_start:.2f}'-{calculated_slab_y_end:.2f}'\n")

    slab_grp = su.create_concrete_slab_group(
        doc,
        utilities_slab_config,
        pile_positions_ft=pile_positions_ft,
        pile_size_in=FOUNDATION.get("pile_actual_size_in", FOUNDATION["pile_size_in"])
    )
else:
    App.Console.PrintMessage("[Build_950Surf] Concrete slab skipped (disabled in BUILD config)\n")

if BUILD.get("include_utilities", False):
    App.Console.PrintMessage("[Build_950Surf] === UTILITIES ===\n")

    # Calculate water stub-up position from pile positions (no hardcoded values)
    # Water stub at west face of pile [4,3] (0-based indices: column 5, row 4 in 1-based)
    water_stub_pile_col = 4  # Pile column index (0-based)
    water_stub_pile_row = 3  # Pile row index (0-based)
    water_stub_pile_x_ft = x_positions_ft[water_stub_pile_col]
    water_stub_pile_y_ft = y_positions_ft[water_stub_pile_row]
    water_pipe_diameter_in = UTILITIES.get("water_service_line_diameter_in", 1.0)
    # West face of pile: pile center X - pile half thickness
    # Pipe center at west face: west face X - pipe radius
    water_stub_west_face_ft = water_stub_pile_x_ft - pile_half_thickness_ft
    water_stub_x_ft = water_stub_west_face_ft - (water_pipe_diameter_in / 2.0) / 12.0

    # Calculate electrical equipment position from pile positions (no hardcoded values)
    # Electrical at east face of pile [3,3] (0-based indices: column 4, row 4 in 1-based)
    elec_pile_col = 3  # Pile column index (0-based)
    elec_pile_row = 3  # Pile row index (0-based)
    elec_pile_x_ft = x_positions_ft[elec_pile_col]
    elec_pile_y_ft = y_positions_ft[elec_pile_row]
    # East face of pile: pile center X + pile half thickness
    elec_equipment_x_ft = elec_pile_x_ft + pile_half_thickness_ft

    # Create utilities config with calculated positions
    utilities_config = dict(UTILITIES)
    utilities_config["water_stub_x_ft"] = water_stub_x_ft
    utilities_config["water_stub_y_ft"] = water_stub_pile_y_ft
    utilities_config["electrical_equipment_x_ft"] = elec_equipment_x_ft
    utilities_config["electrical_equipment_y_ft"] = elec_pile_y_ft
    # Also set electrical_stub for backward compatibility (offset 6" north from water)
    utilities_config["electrical_stub_x_ft"] = elec_equipment_x_ft
    utilities_config["electrical_stub_y_ft"] = elec_pile_y_ft + 0.5  # 6" offset north

    App.Console.PrintMessage(f"[Build_950Surf]   Water stub-up at pile [{water_stub_pile_col},{water_stub_pile_row}] west face: X={water_stub_x_ft:.3f}', Y={water_stub_pile_y_ft:.5f}'\n")
    App.Console.PrintMessage(f"[Build_950Surf]   Electrical equipment at pile [{elec_pile_col},{elec_pile_row}] east face: X={elec_equipment_x_ft:.5f}', Y={elec_pile_y_ft:.5f}'\n")

    # Pass STAIRS, FOUNDATION, and LOT configs for foot wash station and pile hose bibs
    utilities_grp = su.create_utilities_group(doc, utilities_config, stairs_config=STAIRS, foundation_config=FOUNDATION, lot_config=LOT)
else:
    App.Console.PrintMessage("[Build_950Surf] Utilities skipped (disabled in BUILD config)\n")

# ============================================================
# SECTION 4.4: DRIVEWAY SLAB (with rebar)
# ============================================================

if BUILD.get("include_driveway", False):
    App.Console.PrintMessage("[Build_950Surf] === DRIVEWAY ===\n")
    # Pass UTILITIES config to create cutouts for water boxes (dependency tracking)
    driveway_grp = su.create_driveway_slab_group(doc, DRIVEWAY, utilities_config=UTILITIES)
else:
    App.Console.PrintMessage("[Build_950Surf] Driveway skipped (disabled in BUILD config)\n")

# ============================================================
# SECTION 4.45: EXTERIOR STAIRS (from slab to floor)
# ============================================================

if BUILD.get("include_stairs", False):
    App.Console.PrintMessage("[Build_950Surf] === EXTERIOR STAIRS ===\n")
    stairs_grp = su.create_exterior_stairs(doc, STAIRS, floor_z_ft=above_grade_ft, slab_z_ft=0.0)
else:
    App.Console.PrintMessage("[Build_950Surf] Exterior stairs skipped (disabled in BUILD config)\n")

# ============================================================
# SECTION 4.5: DECK JOISTS (installed BEFORE first floor sheathing)
# ============================================================

if BUILD.get("include_deck_joists", False):
    App.Console.PrintMessage("[Build_950Surf] Building deck joists...\n")

    # Import modules (already in sys.path via _macros_dir)
    import deck_assemblies as da
    import lumber_common as lc
    import parts
    importlib.reload(da)
    importlib.reload(parts)

    # Load catalog for deck assemblies
    catalog_path = os.path.join(_design_house_root, "lumber", "lumber_catalog.csv")
    catalog_rows = lc.load_catalog(catalog_path)

    deck_z_base_in = above_grade_ft * 12.0  # Same level as foundation top

    # front_deck_y_ft is calculated at module level (line ~188) from DECKS config
    # Rear deck: starts at back edge of floor area (3x3 grid of 16x16 modules = 48' deep)
    floor_depth_ft = (FIRST_FLOOR["module_16x16_depth_in"] * 3) / 12.0  # 3 rows x 16' = 48'
    rear_deck_y_ft = front_setback_ft + y_spacing_ft + floor_depth_ft

    # Deck X positioning: snap to first floor joists
    # Floor width from module dimensions (3x3 grid of 16x16 modules = 48' wide)
    floor_width_ft_local = (FIRST_FLOOR["module_16x16_width_in"] * 3) / 12.0  # 3 columns x 16' = 48'
    floor_start_x_ft = (lot_x_ft - floor_width_ft_local) / 2.0  # Center floor on lot
    deck_left_x_ft = floor_start_x_ft  # Snap deck left edge to floor left edge

    deck_joist_assemblies = []

    # ============================================================
    # FRONT DECK: 3 modules of 16x12 (joists run N-S, rims run E-W)
    # Module layout: 16' wide x 12' deep, deck boards run E-W
    # ============================================================
    App.Console.PrintMessage("[Build_950Surf]   Creating front deck joists (3 x 16x12 modules)...\n")

    # NOTE: Blocking is NOT created here in the joist modules. Instead, blocking is added
    # after deck surface is complete (in SECTION 8D) so it can be properly positioned
    # around sister joists at seam positions.

    # Left module (west)
    front_deck_left = parts.create_deck_module_front_16x12(
        doc,
        catalog_rows,
        assembly_name="Front_Deck_Left_16x12",
        make_pressure_treated=True,
        blocking_positions_in=None,  # Blocking added later with deck surface
    )
    lc.place_assembly_at(
        front_deck_left,
        x_ft=deck_left_x_ft,
        y_ft=front_deck_y_ft,
        z_ft=above_grade_ft,
    )
    deck_joist_assemblies.append(front_deck_left)

    # Center module
    front_deck_center = parts.create_deck_module_front_16x12(
        doc,
        catalog_rows,
        assembly_name="Front_Deck_Center_16x12",
        make_pressure_treated=True,
        blocking_positions_in=None,  # Blocking added later with deck surface
    )
    lc.snap_assembly_corner_to_corner(
        front_deck_center, front_deck_left, target_corner="bottom_right", assembly_corner="bottom_left"
    )
    deck_joist_assemblies.append(front_deck_center)

    # Right module (east) - with stair opening if configured
    stair_opening_config = DECKS.get("stair_opening", None)
    front_deck_right = parts.create_deck_module_front_16x12(
        doc,
        catalog_rows,
        assembly_name="Front_Deck_Right_16x12",
        make_pressure_treated=True,
        blocking_positions_in=None,  # Blocking added later with deck surface
        stair_opening=stair_opening_config,
    )
    lc.snap_assembly_corner_to_corner(
        front_deck_right, front_deck_center, target_corner="bottom_right", assembly_corner="bottom_left"
    )
    deck_joist_assemblies.append(front_deck_right)

    # Calculate filler module width from actual assembly dimensions
    # Floor modules are 195" wide (16' + 3" for rims), front deck modules are 192" wide (16' flat)
    # Gap = (floor_module_width x 3) - (front_deck_module_width x 3)
    floor_module_width_in = FIRST_FLOOR["module_16x16_width_in"]  # 195"
    front_deck_module_width_in = 192.0  # 16' flat (from create_deck_module_front_16x12)
    filler_width_in = (floor_module_width_in * 3) - (front_deck_module_width_in * 3)  # 9"
    filler_width_ft = filler_width_in / 12.0

    App.Console.PrintMessage(f"[Build_950Surf]   Creating front deck filler module ({filler_width_in:.1f}\" wide)...\n")

    # Filler module (east side) - small module to square out front deck with floor joists
    front_deck_filler = parts.create_deck_module_front(
        doc,
        catalog_rows,
        rim_length_ft=filler_width_ft,  # Calculated from floor module width difference
        joist_length_ft=12.0,  # Same depth as main modules
        assembly_name="Front_Deck_Filler_East",
        joist_label="2x12x144",  # 12' joists
        rim_label="2x12x96",  # Use 8' stock, field cut to filler width
        make_pressure_treated=True,
        blocking_positions_in=None,  # Blocking added later with deck surface
    )
    lc.snap_assembly_corner_to_corner(
        front_deck_filler, front_deck_right, target_corner="bottom_right", assembly_corner="bottom_left"
    )
    deck_joist_assemblies.append(front_deck_filler)

    # Rear deck joists: 3 x 16x4 modules + 9" filler (same pattern as front deck)
    # Using 4' depth modules (joists cut from 8' stock)
    rear_deck_depth_ft = DECKS["rear_deck_depth_ft"]  # 4' from config
    App.Console.PrintMessage(f"[Build_950Surf]   Creating rear deck joists (3 x 16x{rear_deck_depth_ft:.0f} modules + filler)...\n")

    # Left module (west)
    rear_deck_joists_left = parts.create_deck_module_front_16x4(
        doc,
        catalog_rows,
        assembly_name="Rear_Deck_Left_16x4",
        make_pressure_treated=True,
    )
    # Position at rear deck origin
    lc.place_assembly_at(rear_deck_joists_left, x_ft=deck_left_x_ft, y_ft=rear_deck_y_ft, z_ft=deck_z_base_in / 12.0)
    deck_joist_assemblies.append(rear_deck_joists_left)

    # Center module
    rear_deck_joists_center = parts.create_deck_module_front_16x4(
        doc,
        catalog_rows,
        assembly_name="Rear_Deck_Center_16x4",
        make_pressure_treated=True,
    )
    lc.snap_assembly_corner_to_corner(
        rear_deck_joists_center, rear_deck_joists_left, target_corner="bottom_right", assembly_corner="bottom_left"
    )
    deck_joist_assemblies.append(rear_deck_joists_center)

    # Right module (east)
    rear_deck_joists_right = parts.create_deck_module_front_16x4(
        doc,
        catalog_rows,
        assembly_name="Rear_Deck_Right_16x4",
        make_pressure_treated=True,
    )
    lc.snap_assembly_corner_to_corner(
        rear_deck_joists_right, rear_deck_joists_center, target_corner="bottom_right", assembly_corner="bottom_left"
    )
    deck_joist_assemblies.append(rear_deck_joists_right)

    # Calculate filler module width (same as front deck)
    # Floor modules are 195" wide, deck modules are 192" wide
    # Gap = (195 x 3) - (192 x 3) = 9"
    rear_deck_module_width_in = 192.0  # 16' flat
    rear_filler_width_in = (floor_module_width_in * 3) - (rear_deck_module_width_in * 3)  # 9"
    rear_filler_width_ft = rear_filler_width_in / 12.0

    App.Console.PrintMessage(f"[Build_950Surf]   Creating rear deck filler module ({rear_filler_width_in:.1f}\" wide)...\n")

    # Filler module (east side) - small module to square out rear deck with floor joists
    rear_deck_joists_filler = parts.create_deck_module_front(
        doc,
        catalog_rows,
        rim_length_ft=rear_filler_width_ft,  # 9" wide
        joist_length_ft=rear_deck_depth_ft,  # Same depth as main modules (4')
        assembly_name="Rear_Deck_Filler_East",
        joist_label="2x12x96",  # 8' stock, field cut to 4'
        rim_label="2x12x96",  # Use 8' stock, field cut to filler width
        make_pressure_treated=True,
    )
    lc.snap_assembly_corner_to_corner(
        rear_deck_joists_filler, rear_deck_joists_right, target_corner="bottom_right", assembly_corner="bottom_left"
    )
    deck_joist_assemblies.append(rear_deck_joists_filler)

    # Create Deck_Joists group
    deck_joists_grp = bc.create_group(doc, "Deck_Joists")
    bc.add_to_group(deck_joists_grp, deck_joist_assemblies)

    App.Console.PrintMessage(f"[Build_950Surf] Deck joists complete ({len(deck_joist_assemblies)} modules).\n")
else:
    App.Console.PrintMessage("[Build_950Surf] Deck joists skipped (disabled in BUILD config)\n")

# ============================================================
# SECTION 4.6: BEACH ELEVATOR (open metal lift)
# Uses front_deck_y_ft (calculated at module level) for positioning
# ============================================================

if BUILD.get("include_elevator", False):
    App.Console.PrintMessage("[Build_950Surf] === BEACH ELEVATOR ===\n")

    # Get elevator config values (user-specified approximate position and size)
    elevator_x_ft = ELEVATOR.get("elevator_x_ft", 42.0)
    platform_depth_ft = ELEVATOR.get("platform_depth_ft", 5.0)
    platform_width_ft = ELEVATOR.get("platform_width_ft", 4.0)
    elev_post_size_in = 4.0  # 4" square steel posts

    # Calculate Y position (north face of elevator posts align with deck rim south face)
    elevator_y_ft = front_deck_y_ft - platform_depth_ft / 2.0 - (elev_post_size_in / 2.0) / 12.0

    App.Console.PrintMessage(f"[Build_950Surf]   Elevator: {platform_width_ft:.1f}' x {platform_depth_ft:.1f}' at X={elevator_x_ft:.1f}'\n")

    # Create elevator with config values (railing code will align opening to posts)
    elevator_config = dict(ELEVATOR)
    elevator_config["elevator_y_ft"] = elevator_y_ft

    elevator_grp = be.create_beach_elevator(doc, elevator_config, foundation_config=FOUNDATION)
else:
    App.Console.PrintMessage("[Build_950Surf] Beach elevator skipped (disabled in BUILD config)\n")

# ============================================================
# SECTION 5: FIRST FLOOR JOISTS (Assembly-Based Modules)
# ============================================================

def create_first_floor_joists(doc, catalog, params, macro_dir):
    """Build first floor using reusable joist module assemblies with snapping.

    Construction Sequence:
        1. Load joist module macros (16x16 assemblies)
        2. Create module instances and position via snapping
        3. NO hard-coded offsets - uses bounding box geometry

    Design Rationale:
        - Reusable modules eliminate code duplication
        - Assembly snapping ensures perfect alignment (0.0000mm gaps)
        - Clean hierarchy: Floor -> Module (assembly) -> Joists + Hardware

    Floor Layout (3x3 grid pattern):
        - Grid uses (row, col) naming like piles: Floor_R{row}_C{col}
        - Row 1 (front), Row 2 (center), Row 3 (back)
        - Col 1 (left/west), Col 2 (middle), Col 3 (right/east)

        Row 1 (front):  16x16 + 16x16 + 16x16 = 48' wide x 16' deep
        Row 2 (center): 16x16 + 16x16 + 16x16 = 48' wide x 16' deep
        Row 3 (back):   16x16 + 16x16 + 16x16 = 48' wide x 16' deep

        Total: 48' wide x 48' deep (9 identical modules)

    Args:
        doc: FreeCAD document
        catalog: Catalog rows from beach_common
        params (dict): Floor parameters with keys:
            - floor_base_z_ft: Z position for floor deck
            - floor_start_x_ft, floor_start_y_ft: Front-left corner position
        macro_dir: Path to this macro's directory

    Returns:
        floor_grp: DocumentObjectGroup containing floor assemblies
    """
    import importlib

    App.Console.PrintMessage("[Build_950Surf] Building first floor joists (assembly-based)...\n")

    # Import lumber modules
    # macro_dir might be empty when running from FreeCADCmd
    if not macro_dir:
        macro_dir = os.getcwd()

    # Import parts modules (already in sys.path via _macros_dir)
    import lumber_common as lc
    import parts
    importlib.reload(lc)
    importlib.reload(parts)

    # Load catalog (use _design_house_root which is already set correctly)
    catalog_path = os.path.join(_design_house_root, "lumber", "lumber_catalog.csv")
    catalog_rows = lc.load_catalog(catalog_path)
    App.Console.PrintMessage(f"[Build_950Surf]   Loaded {len(catalog_rows)} catalog entries\n")

    modules = []

    # Calculate floor start position (centered on lot)
    module_width_ft = FIRST_FLOOR["module_16x16_width_in"] / 12.0
    floor_width_ft = module_width_ft * 3  # 3 columns x 16' = 48'
    floor_start_x_ft = (params["lot_x_ft"] - floor_width_ft) / 2.0  # Center on lot

    # ============================================================
    # CREATE FLOOR MODULES IN 3x3 GRID PATTERN
    # All modules are 16'x16' for uniform construction
    # Grid: 3 rows x 3 columns = 9 modules = 48' x 48'
    # Row 1 = front (south), Row 2 = center, Row 3 = back (north)
    # Col 1 = left (west), Col 2 = middle, Col 3 = right (east)
    # ============================================================

    # Store modules by grid position for snapping reference
    grid = {}  # grid[(row, col)] = module

    for row in range(1, 4):  # Rows 1, 2, 3 (front, center, back)
        row_name = {1: "Front", 2: "Center", 3: "Back"}[row]
        App.Console.PrintMessage(f"[Build_950Surf]   === ROW {row} ({row_name.upper()}) ===\n")

        for col in range(1, 4):  # Columns 1, 2, 3 (left, middle, right)
            assembly_name = f"Floor_R{row}_C{col}_16x16"

            # All floor modules are standard 16x16 (no stair cutout in floor - stairs in front deck)
            App.Console.PrintMessage(f"[Build_950Surf]   Creating {assembly_name}...\n")
            module = parts.create_joist_module_16x16(
                doc, catalog_rows, assembly_name=assembly_name, make_pressure_treated=False
            )

            # Position module using snapping
            if row == 1 and col == 1:
                # First module (R1,C1): place at absolute position (anchor for entire floor)
                lc.place_assembly_at(module, x_ft=floor_start_x_ft, y_ft=params["floor_start_y_ft"], z_ft=params["floor_base_z_ft"])
            elif col == 1:
                # First column of subsequent rows: snap to previous row's first column
                prev_module = grid[(row - 1, 1)]
                lc.snap_assembly_corner_to_corner(module, prev_module, target_corner="top_left", assembly_corner="bottom_left")
            else:
                # Columns 2 and 3: snap to left neighbor in same row
                left_neighbor = grid[(row, col - 1)]
                lc.snap_assembly_corner_to_corner(module, left_neighbor, target_corner="bottom_right", assembly_corner="bottom_left")

            grid[(row, col)] = module
            modules.append(module)

    # ============================================================
    # GROUP ALL MODULES
    # ============================================================
    floor_grp = bc.create_group(doc, "First_Floor_Joists")
    bc.add_to_group(floor_grp, modules)

    App.Console.PrintMessage(f"[Build_950Surf]   (done) Created {len(modules)} floor modules (3x3 grid = 48' x 48')\n")
    App.Console.PrintMessage("[Build_950Surf] First floor joists complete.\\n")

    return floor_grp

# Create first floor joists
# Calculate floor start position from module dimensions in config
# Floor layout: 3x3 grid of 16'x16' modules = 48' x 48'
floor_width_ft = (FIRST_FLOOR["module_16x16_width_in"] * 3) / 12.0  # 3 columns x 16' = 48'
floor_depth_ft = (FIRST_FLOOR["module_16x16_depth_in"] * 3) / 12.0  # 3 rows x 16' = 48'

if BUILD.get("include_first_floor", False):
    floor_params = {
        "floor_base_z_ft": above_grade_ft,
        "floor_start_x_ft": (lot_x_ft - floor_width_ft) / 2.0,  # Center on lot
        "floor_start_y_ft": front_setback_ft + y_spacing_ft,  # Start at second row of piles
        "lot_x_ft": lot_x_ft,  # Pass lot width for center calculation
    }

    floor_grp = create_first_floor_joists(doc, catalog, floor_params, _macros_dir)
else:
    App.Console.PrintMessage("[Build_950Surf] First floor joists skipped (disabled in BUILD config)\n")

# ============================================================
# SECTION 6: FIRST FLOOR SHEATHING
# ============================================================
# NOTE: Stair opening is now in front deck area (not floor joists)
# The front deck joist module will include stair opening framing (future implementation)

if BUILD.get("include_first_floor", False):
    App.Console.PrintMessage("[Build_950Surf] Adding first floor sheathing...\n")

    # Import lumber modules for sheathing (already in sys.path via _macros_dir)
    import importlib

    import lumber_common as lc
    import parts
    importlib.reload(lc)
    importlib.reload(parts)

    # Load lumber catalog for sheathing panels
    catalog_path = os.path.join(_design_house_root, "lumber", "lumber_catalog.csv")
    catalog_rows = lc.load_catalog(catalog_path)

    # Create a simple bounding box from known floor layout dimensions
    # Floor is 40.75' x 40' (from params above)
    floor_start_x_mm = bc.ft(floor_params["floor_start_x_ft"])
    floor_start_y_mm = bc.ft(floor_params["floor_start_y_ft"])
    floor_width_mm = bc.ft(floor_width_ft)
    floor_depth_mm = bc.ft(floor_depth_ft)
    joist_depth_in = FIRST_FLOOR["joist_depth_in"]
    floor_z_top_mm = bc.ft(floor_params["floor_base_z_ft"]) + bc.inch(joist_depth_in)  # Top of joists

    # Create a simple bbox-like object
    class SimpleBBox:
        def __init__(self, xmin, ymin, xmax, ymax, zmax):
            self.XMin = xmin
            self.YMin = ymin
            self.XMax = xmax
            self.YMax = ymax
            self.ZMax = zmax
            self.XLength = xmax - xmin
            self.YLength = ymax - ymin

    floor_bbox = SimpleBBox(
        floor_start_x_mm,
        floor_start_y_mm,
        floor_start_x_mm + floor_width_mm,
        floor_start_y_mm + floor_depth_mm,
        floor_z_top_mm
    )

    # Create sheathing panels (exclude deck areas from config)
    deck_exclusion_ft = FIRST_FLOOR["sheathing_deck_exclusion_ft"]
    sheathing_grp = parts.create_sheathing_for_floor(
        doc,
        catalog_rows,
        floor_bbox,
        z_offset_in=0.0,  # Sheathing sits ON TOP of joists
        group_name="First_Floor_Sheathing",
        panel_label=FIRST_FLOOR["sheathing_stock"],
        exclude_left_ft=deck_exclusion_ft,
        exclude_right_ft=deck_exclusion_ft,
    )

    App.Console.PrintMessage("[Build_950Surf] First floor sheathing complete.\n")

    # Create top-level First_Floor group to organize joists and sheathing
    # (walls will be added to this group later)
    first_floor_parent = bc.create_group(doc, "First_Floor")
    bc.add_to_group(first_floor_parent, [floor_grp, sheathing_grp])
    App.Console.PrintMessage("[Build_950Surf] First floor joists and sheathing organized.\n")

# ============================================================
# SECTION 7: WALLS (Front and Rear - BUTT walls)
# ============================================================
# FRAMING APPROACH: Front/rear walls are BUTT walls, side walls are THROUGH walls
#   - Front/rear walls run full width (40') at sheathing edges (this section)
#   - Side walls fit BETWEEN front/rear walls (see Section 8B)
#   - Butt walls terminate at corners; through walls provide continuous plates

if BUILD.get("include_walls", False):
    App.Console.PrintMessage("[Build_950Surf] Building walls...\n")

    # Import wall assembly module
    import wall_assemblies as wa
    importlib.reload(wa)

    # Wall positioning parameters
    # Walls sit on top of floor sheathing
    joist_depth_in = FIRST_FLOOR["joist_depth_in"]
    sheathing_thickness_in = FIRST_FLOOR["sheathing_thickness_in"]
    wall_z_base_in = (floor_params["floor_base_z_ft"] * 12.0) + joist_depth_in + sheathing_thickness_in

    # Front wall: aligned with sheathing, offset from config
    sheathing_x_start_ft = floor_params["floor_start_x_ft"] + deck_exclusion_ft
    sheathing_y_start_ft = floor_params["floor_start_y_ft"]

    # Wall positioning from config
    wall_offset_ft = WALLS["front_wall_offset_from_sheathing_ft"]
    front_wall_x_start_ft = sheathing_x_start_ft + wall_offset_ft
    front_wall_y_ft = sheathing_y_start_ft

    # Sheathing width = 40' (5 x 8' wall modules)
    sheathing_width_ft = 40.0

    # Wall assemblies are created in default orientation (Y = wall length)
    # Then rotated 90 degrees around Z to run along X (front of house)
    # After rotation: X = wall length (along front), Y = wall thickness (depth into house), Z = vertical

    # Front wall module positions (left to right, 8' each)
    # Module layout: Window | Door | Window | Door | Window = 40' total
    # Matches rear wall layout for symmetry
    wall_assemblies = []

    # Get wall module width from config
    wall_module_width_ft = WALLS["wall_module_width_ft"]

    # Helper to rotate wall 90 degrees around Z axis
    def rotate_wall_90(wall, x_offset_ft):
        """Rotate wall 90 degrees CCW around Z axis and snap bottom-left corner to sheathing"""
        # Wall is created at origin with orientation: X=thickness, Y=length, Z=vertical
        # Rotate 90 degrees CCW around Z: new orientation is X=length, Y=thickness, Z=vertical
        wall.Placement.Rotation = App.Rotation(App.Vector(0, 0, 1), 90)

        # Snap bottom-left corner of wall to sheathing
        wall_x_ft = front_wall_x_start_ft + x_offset_ft
        wall_y_ft_corner = front_wall_y_ft

        wall.Placement.Base = App.Vector(
            bc.ft(wall_x_ft),
            bc.ft(wall_y_ft_corner),
            bc.inch(wall_z_base_in)
        )

    # Module 1: Window (far left)
    App.Console.PrintMessage("[Build_950Surf]   Creating front wall module 1 (window)...\n")
    wall_1 = wa.create_window_wall_double_3x5(
        doc, catalog_rows, assembly_name="Front_Wall_1_Window",
        x_base=0.0, y_base=0.0, z_base=0.0,
        make_pressure_treated=False, use_debug_colors=False,
    )
    rotate_wall_90(wall_1, x_offset_ft=0.0)
    wall_assemblies.append(wall_1)

    # Module 2: Sliding door (left)
    App.Console.PrintMessage("[Build_950Surf]   Creating front wall module 2 (door)...\n")
    wall_2 = wa.create_sliding_door_72x80(
        doc, catalog_rows, assembly_name="Front_Wall_2_Door",
        x_base=0.0, y_base=0.0, z_base=0.0,
        make_pressure_treated=False, use_debug_colors=False,
    )
    rotate_wall_90(wall_2, x_offset_ft=wall_module_width_ft * 1.0)
    wall_assemblies.append(wall_2)

    # Module 3: Window (center)
    App.Console.PrintMessage("[Build_950Surf]   Creating front wall module 3 (window)...\n")
    wall_3 = wa.create_window_wall_double_3x5(
        doc, catalog_rows, assembly_name="Front_Wall_3_Window",
        x_base=0.0, y_base=0.0, z_base=0.0,
        make_pressure_treated=False, use_debug_colors=False,
    )
    rotate_wall_90(wall_3, x_offset_ft=wall_module_width_ft * 2.0)
    wall_assemblies.append(wall_3)

    # Module 4: Sliding door (right)
    App.Console.PrintMessage("[Build_950Surf]   Creating front wall module 4 (door)...\n")
    wall_4 = wa.create_sliding_door_72x80(
        doc, catalog_rows, assembly_name="Front_Wall_4_Door",
        x_base=0.0, y_base=0.0, z_base=0.0,
        make_pressure_treated=False, use_debug_colors=False,
    )
    rotate_wall_90(wall_4, x_offset_ft=wall_module_width_ft * 3.0)
    wall_assemblies.append(wall_4)

    # Module 5: Window (far right)
    App.Console.PrintMessage("[Build_950Surf]   Creating front wall module 5 (window)...\n")
    wall_5 = wa.create_window_wall_double_3x5(
        doc, catalog_rows, assembly_name="Front_Wall_5_Window",
        x_base=0.0, y_base=0.0, z_base=0.0,
        make_pressure_treated=False, use_debug_colors=False,
    )
    rotate_wall_90(wall_5, x_offset_ft=wall_module_width_ft * 4.0)
    wall_assemblies.append(wall_5)

    # Create Front_Wall group to organize all wall assemblies
    front_wall_grp = bc.create_group(doc, "Front_Wall")
    bc.add_to_group(front_wall_grp, wall_assemblies)

    App.Console.PrintMessage(f"[Build_950Surf] Front wall complete ({len(wall_assemblies)} modules).\n")

# ============================================================
# SECTION 8: REAR WALL (Window | Door | Window | Door | Window)
# ============================================================

if BUILD.get("include_walls", False):
    App.Console.PrintMessage("[Build_950Surf] Building rear wall...\n")

    # Rear wall positioning: mirror of front wall, at back edge of sheathing
    # Sheathing depth from floor module depths
    sheathing_depth_ft = floor_depth_ft
    rear_wall_x_start_ft = front_wall_x_start_ft
    rear_wall_y_ft = sheathing_y_start_ft + sheathing_depth_ft  # Back edge of sheathing
    rear_wall_assemblies = []

    # Get wall thickness from config
    wall_thickness_in = WALLS["wall_thickness_in"]

    # Helper to rotate and position rear wall
    def rotate_rear_wall_90(wall, x_offset_ft):
        """Rotate wall 90 degrees CCW around Z axis and position at rear of house"""
        wall.Placement.Rotation = App.Rotation(App.Vector(0, 0, 1), 90)

        # Position at rear edge, accounting for wall thickness
        wall_x_ft = rear_wall_x_start_ft + x_offset_ft
        wall_y_ft_corner = rear_wall_y_ft - (wall_thickness_in / 12.0)

        wall.Placement.Base = App.Vector(
            bc.ft(wall_x_ft),
            bc.ft(wall_y_ft_corner),
            bc.inch(wall_z_base_in)
        )

    # Rear wall module layout: Window | Door | Window | Door | Window = 40' total
    # Module 1: Window (far left)
    App.Console.PrintMessage("[Build_950Surf]   Creating rear wall module 1 (window)...\n")
    rear_1 = wa.create_window_wall_double_3x5(
        doc, catalog_rows, assembly_name="Rear_Wall_1_Window",
        x_base=0.0, y_base=0.0, z_base=0.0,
        make_pressure_treated=False, use_debug_colors=False,
    )
    rotate_rear_wall_90(rear_1, x_offset_ft=0.0)
    rear_wall_assemblies.append(rear_1)

    # Module 2: Sliding door (left)
    App.Console.PrintMessage("[Build_950Surf]   Creating rear wall module 2 (door)...\n")
    rear_2 = wa.create_sliding_door_72x80(
        doc, catalog_rows, assembly_name="Rear_Wall_2_Door",
        x_base=0.0, y_base=0.0, z_base=0.0,
        make_pressure_treated=False, use_debug_colors=False,
    )
    rotate_rear_wall_90(rear_2, x_offset_ft=wall_module_width_ft * 1.0)
    rear_wall_assemblies.append(rear_2)

    # Module 3: Window (center)
    App.Console.PrintMessage("[Build_950Surf]   Creating rear wall module 3 (window)...\n")
    rear_3 = wa.create_window_wall_double_3x5(
        doc, catalog_rows, assembly_name="Rear_Wall_3_Window",
        x_base=0.0, y_base=0.0, z_base=0.0,
        make_pressure_treated=False, use_debug_colors=False,
    )
    rotate_rear_wall_90(rear_3, x_offset_ft=wall_module_width_ft * 2.0)
    rear_wall_assemblies.append(rear_3)

    # Module 4: Sliding door (right)
    App.Console.PrintMessage("[Build_950Surf]   Creating rear wall module 4 (door)...\n")
    rear_4 = wa.create_sliding_door_72x80(
        doc, catalog_rows, assembly_name="Rear_Wall_4_Door",
        x_base=0.0, y_base=0.0, z_base=0.0,
        make_pressure_treated=False, use_debug_colors=False,
    )
    rotate_rear_wall_90(rear_4, x_offset_ft=wall_module_width_ft * 3.0)
    rear_wall_assemblies.append(rear_4)

    # Module 5: Window (far right)
    App.Console.PrintMessage("[Build_950Surf]   Creating rear wall module 5 (window)...\n")
    rear_5 = wa.create_window_wall_double_3x5(
        doc, catalog_rows, assembly_name="Rear_Wall_5_Window",
        x_base=0.0, y_base=0.0, z_base=0.0,
        make_pressure_treated=False, use_debug_colors=False,
    )
    rotate_rear_wall_90(rear_5, x_offset_ft=wall_module_width_ft * 4.0)
    rear_wall_assemblies.append(rear_5)

    # Create Rear_Wall group
    rear_wall_grp = bc.create_group(doc, "Rear_Wall")
    bc.add_to_group(rear_wall_grp, rear_wall_assemblies)

    App.Console.PrintMessage(f"[Build_950Surf] Rear wall complete ({len(rear_wall_assemblies)} modules).\n")

    # Add front and rear walls to First_Floor parent group
    bc.add_to_group(first_floor_parent, [front_wall_grp, rear_wall_grp])
    App.Console.PrintMessage("[Build_950Surf] Front and rear walls organized under First_Floor.\n")

# ============================================================
# SECTION 8B: SIDE WALLS (left/west and right/east)
# ============================================================
# FRAMING APPROACH: Front/rear walls are BUTT walls, side walls are THROUGH walls
#   - Front/rear walls run full width (40') at sheathing edges
#   - Side walls run north-south, fitting BETWEEN front and rear walls
#   - This provides continuous structural plates on the side walls for load transfer
#
# Side walls run north-south (along Y axis) from front wall to rear wall
# Floor depth is 48' (3 rows x 16')
# Side walls sit ON the sheathing (inside the front/rear walls) using corner alignment:
#   - Front module: 16' (192"), starts inside front wall
#   - Center module: 185" (16' minus 7" for wall overlap at corners)
#   - Rear module: 16' (192"), ends inside rear wall

if BUILD.get("include_walls", False):
    App.Console.PrintMessage("[Build_950Surf] Building side walls...\n")

    # Side wall positioning using corner alignment
    wall_thickness_in = WALLS["wall_thickness_in"]  # 3.5"
    wall_thickness_ft = wall_thickness_in / 12.0

    # Module lengths
    full_module_length_in = 192.0  # 16' = 192"
    center_module_length_in = 185.0  # 16' - 7" = 185" (3.5" overlap at each end)

    # X positions: walls sit ON sheathing (moved inward by wall thickness)
    # Left wall: west edge of wall aligns with west edge of sheathing
    left_wall_x_ft = sheathing_x_start_ft
    # Right wall: east edge of wall aligns with east edge of sheathing
    right_wall_x_ft = sheathing_x_start_ft + sheathing_width_ft - wall_thickness_ft

    # Y positions: walls fit INSIDE front/rear walls (corner alignment)
    # Front module starts inside front wall (at front wall's inside face)
    side_wall_y_start_ft = sheathing_y_start_ft + wall_thickness_ft

    # === LEFT (WEST) WALL ===
    App.Console.PrintMessage("[Build_950Surf]   Building left (west) side wall...\n")
    left_wall_assemblies = []

    # Module 1: Front (south) 16' section - starts inside front wall
    App.Console.PrintMessage("[Build_950Surf]     Creating left wall module 1 (16' solid stud)...\n")
    left_wall_1 = wa.create_solid_stud_wall_16ft(
        doc, catalog_rows, assembly_name="Left_Wall_1_Solid",
        x_base=0.0, y_base=0.0, z_base=0.0,
        make_pressure_treated=False, use_debug_colors=False,
    )
    # No rotation needed - wall is already oriented Y=length (north-south)
    # Position: X at left wall position, Y at front, Z at wall base
    left_wall_1.Placement.Base = App.Vector(
        bc.ft(left_wall_x_ft),
        bc.ft(side_wall_y_start_ft),
        bc.inch(wall_z_base_in)
    )
    left_wall_assemblies.append(left_wall_1)

    # Module 2: Center section - 185" (reduced from 16' to fit between modules)
    # Y position: starts after front module (16' = 192")
    module_2_y_start_ft = side_wall_y_start_ft + (full_module_length_in / 12.0)
    App.Console.PrintMessage("[Build_950Surf]     Creating left wall module 2 (185\" solid stud)...\n")
    left_wall_2 = wa.create_solid_stud_wall(
        doc, catalog_rows, wall_length_in=center_module_length_in,
        assembly_name="Left_Wall_2_Solid",
        x_base=0.0, y_base=0.0, z_base=0.0,
        make_pressure_treated=False, use_debug_colors=False,
    )
    left_wall_2.Placement.Base = App.Vector(
        bc.ft(left_wall_x_ft),
        bc.ft(module_2_y_start_ft),
        bc.inch(wall_z_base_in)
    )
    left_wall_assemblies.append(left_wall_2)

    # Module 3: Rear (north) 16' section - ends inside rear wall
    # Y position: starts after center module (192" + 185" = 377")
    module_3_y_start_ft = module_2_y_start_ft + (center_module_length_in / 12.0)
    App.Console.PrintMessage("[Build_950Surf]     Creating left wall module 3 (16' solid stud)...\n")
    left_wall_3 = wa.create_solid_stud_wall_16ft(
        doc, catalog_rows, assembly_name="Left_Wall_3_Solid",
        x_base=0.0, y_base=0.0, z_base=0.0,
        make_pressure_treated=False, use_debug_colors=False,
    )
    left_wall_3.Placement.Base = App.Vector(
        bc.ft(left_wall_x_ft),
        bc.ft(module_3_y_start_ft),
        bc.inch(wall_z_base_in)
    )
    left_wall_assemblies.append(left_wall_3)

    # Create Left_Wall group
    left_wall_grp = bc.create_group(doc, "Left_Wall")
    bc.add_to_group(left_wall_grp, left_wall_assemblies)
    App.Console.PrintMessage(f"[Build_950Surf]   Left wall complete ({len(left_wall_assemblies)} modules).\n")

    # === RIGHT (EAST) WALL ===
    App.Console.PrintMessage("[Build_950Surf]   Building right (east) side wall...\n")
    right_wall_assemblies = []

    # Module 1: Front (south) 16' section - starts inside front wall
    App.Console.PrintMessage("[Build_950Surf]     Creating right wall module 1 (16' solid stud)...\n")
    right_wall_1 = wa.create_solid_stud_wall_16ft(
        doc, catalog_rows, assembly_name="Right_Wall_1_Solid",
        x_base=0.0, y_base=0.0, z_base=0.0,
        make_pressure_treated=False, use_debug_colors=False,
    )
    right_wall_1.Placement.Base = App.Vector(
        bc.ft(right_wall_x_ft),
        bc.ft(side_wall_y_start_ft),
        bc.inch(wall_z_base_in)
    )
    right_wall_assemblies.append(right_wall_1)

    # Module 2: Center section - 185" (reduced from 16' to fit between modules)
    # Y position: same as left wall module 2
    App.Console.PrintMessage("[Build_950Surf]     Creating right wall module 2 (185\" solid stud)...\n")
    right_wall_2 = wa.create_solid_stud_wall(
        doc, catalog_rows, wall_length_in=center_module_length_in,
        assembly_name="Right_Wall_2_Solid",
        x_base=0.0, y_base=0.0, z_base=0.0,
        make_pressure_treated=False, use_debug_colors=False,
    )
    right_wall_2.Placement.Base = App.Vector(
        bc.ft(right_wall_x_ft),
        bc.ft(module_2_y_start_ft),
        bc.inch(wall_z_base_in)
    )
    right_wall_assemblies.append(right_wall_2)

    # Module 3: Rear (north) 16' section - ends inside rear wall
    # Y position: same as left wall module 3
    App.Console.PrintMessage("[Build_950Surf]     Creating right wall module 3 (16' solid stud)...\n")
    right_wall_3 = wa.create_solid_stud_wall_16ft(
        doc, catalog_rows, assembly_name="Right_Wall_3_Solid",
        x_base=0.0, y_base=0.0, z_base=0.0,
        make_pressure_treated=False, use_debug_colors=False,
    )
    right_wall_3.Placement.Base = App.Vector(
        bc.ft(right_wall_x_ft),
        bc.ft(module_3_y_start_ft),
        bc.inch(wall_z_base_in)
    )
    right_wall_assemblies.append(right_wall_3)

    # Create Right_Wall group
    right_wall_grp = bc.create_group(doc, "Right_Wall")
    bc.add_to_group(right_wall_grp, right_wall_assemblies)
    App.Console.PrintMessage(f"[Build_950Surf]   Right wall complete ({len(right_wall_assemblies)} modules).\n")

    # Add side walls to First_Floor parent group
    bc.add_to_group(first_floor_parent, [left_wall_grp, right_wall_grp])
    App.Console.PrintMessage("[Build_950Surf] Side walls organized under First_Floor.\n")

# ============================================================
# SECTION 8C: INTERIOR WALL (center N-S wall on E-W centerline)
# ============================================================
# Interior wall runs north-south along the center of the floor (20' from each side)
# Same construction as side walls: 3 modules (16' + 185" + 16')
# Wall fits BETWEEN front and rear walls (same Y positions as side walls)

if BUILD.get("include_walls", False):
    App.Console.PrintMessage("[Build_950Surf] Building interior center wall...\n")

    # Interior wall X position: center of sheathing width (40' / 2 = 20')
    # Wall center should be at centerline, so subtract half wall thickness
    interior_wall_x_ft = sheathing_x_start_ft + (sheathing_width_ft / 2.0) - (wall_thickness_ft / 2.0)

    interior_wall_assemblies = []

    # Module 1: Front (south) 16' section - starts inside front wall
    App.Console.PrintMessage("[Build_950Surf]   Creating interior wall module 1 (16' solid stud)...\n")
    interior_wall_1 = wa.create_solid_stud_wall_16ft(
        doc, catalog_rows, assembly_name="Interior_Wall_1_Solid",
        x_base=0.0, y_base=0.0, z_base=0.0,
        make_pressure_treated=False, use_debug_colors=False,
    )
    interior_wall_1.Placement.Base = App.Vector(
        bc.ft(interior_wall_x_ft),
        bc.ft(side_wall_y_start_ft),
        bc.inch(wall_z_base_in)
    )
    interior_wall_assemblies.append(interior_wall_1)

    # Module 2: Center section - 185" (same as side walls)
    App.Console.PrintMessage("[Build_950Surf]   Creating interior wall module 2 (185\" solid stud)...\n")
    interior_wall_2 = wa.create_solid_stud_wall(
        doc, catalog_rows, wall_length_in=center_module_length_in,
        assembly_name="Interior_Wall_2_Solid",
        x_base=0.0, y_base=0.0, z_base=0.0,
        make_pressure_treated=False, use_debug_colors=False,
    )
    interior_wall_2.Placement.Base = App.Vector(
        bc.ft(interior_wall_x_ft),
        bc.ft(module_2_y_start_ft),
        bc.inch(wall_z_base_in)
    )
    interior_wall_assemblies.append(interior_wall_2)

    # Module 3: Rear (north) 16' section - ends inside rear wall
    App.Console.PrintMessage("[Build_950Surf]   Creating interior wall module 3 (16' solid stud)...\n")
    interior_wall_3 = wa.create_solid_stud_wall_16ft(
        doc, catalog_rows, assembly_name="Interior_Wall_3_Solid",
        x_base=0.0, y_base=0.0, z_base=0.0,
        make_pressure_treated=False, use_debug_colors=False,
    )
    interior_wall_3.Placement.Base = App.Vector(
        bc.ft(interior_wall_x_ft),
        bc.ft(module_3_y_start_ft),
        bc.inch(wall_z_base_in)
    )
    interior_wall_assemblies.append(interior_wall_3)

    # Create Interior_Wall group
    interior_wall_grp = bc.create_group(doc, "Interior_Wall")
    bc.add_to_group(interior_wall_grp, interior_wall_assemblies)
    App.Console.PrintMessage(f"[Build_950Surf]   Interior wall complete ({len(interior_wall_assemblies)} modules).\n")

    # Add interior wall to First_Floor parent group
    bc.add_to_group(first_floor_parent, [interior_wall_grp])
    App.Console.PrintMessage("[Build_950Surf] Interior wall organized under First_Floor.\n")

# ============================================================
# SECTION 8D: DECK SURFACE (boards, installed BEFORE second floor)
# ============================================================
# Realistic build order: deck boards go on before second floor joists/beams
# This allows workers to safely walk on the deck while framing the second floor
#
# UNIFIED DECK SURFACE APPROACH:
# - One assembly for entire deck perimeter
# - Picture frame with mitered corners around outer edge
# - Zones define board direction based on joist orientation
# - Field boards fill each zone, perpendicular to joists

if BUILD.get("include_deck_surface", False):
    App.Console.PrintMessage("[Build_950Surf] Building unified deck surface...\n")

    # ============================================================
    # Calculate deck perimeter and zone boundaries from actual assemblies
    # ============================================================
    # Derive frame boundaries from placed joist assemblies to ensure perfect alignment
    # rather than recalculating from config (which can drift from actual positions)

    # Get bounding boxes of front and rear deck assemblies
    # The bounding box is in local coordinates, so we need to add the assembly's Placement.Base
    # to get global coordinates (FreeCAD uses mm internally)

    def get_global_bbox(assembly):
        """Get assembly bounding box in global coordinates (mm)."""
        local_bbox = lc.get_assembly_bbox(assembly)
        placement = assembly.Placement.Base
        return {
            "XMin": local_bbox.XMin + placement.x,
            "XMax": local_bbox.XMax + placement.x,
            "YMin": local_bbox.YMin + placement.y,
            "YMax": local_bbox.YMax + placement.y,
            "ZMin": local_bbox.ZMin + placement.z,
            "ZMax": local_bbox.ZMax + placement.z,
        }

    # Front deck: use leftmost module for X min and Y min (south edge)
    front_deck_left_bbox = get_global_bbox(front_deck_left)
    front_deck_filler_bbox = get_global_bbox(front_deck_filler)

    # Rear deck: use filler module for Y max (north edge) and X max (east edge)
    rear_deck_left_bbox = get_global_bbox(rear_deck_joists_left)
    rear_deck_filler_bbox = get_global_bbox(rear_deck_joists_filler)

    # Convert mm to inches (using lumber_common constant)
    mm_to_in = lc.INCH_PER_MM

    # Deck frame boundaries from actual assembly positions (global coordinates)
    deck_frame_x_min_in = front_deck_left_bbox["XMin"] * mm_to_in  # West edge from front deck left
    deck_frame_x_max_in = front_deck_filler_bbox["XMax"] * mm_to_in  # East edge from front deck filler
    deck_frame_y_min_in = front_deck_left_bbox["YMin"] * mm_to_in  # South edge from front deck front rim
    deck_frame_y_max_in = rear_deck_filler_bbox["YMax"] * mm_to_in  # North edge from rear deck back rim

    App.Console.PrintMessage(f"[Build_950Surf]   Deck frame from assemblies: X=[{deck_frame_x_min_in:.2f}, {deck_frame_x_max_in:.2f}], Y=[{deck_frame_y_min_in:.2f}, {deck_frame_y_max_in:.2f}]\n")

    # Sheathing boundaries (where deck boards DON'T go)
    # These define the interior floor area - derived from FIRST FLOOR config, NOT deck assemblies
    # This ensures deck boards stop exactly at the first floor sheathing edge
    side_deck_width_ft = FIRST_FLOOR.get("sheathing_deck_exclusion_ft", 4.375)  # ~4' overhang
    side_deck_width_in = side_deck_width_ft * 12.0

    # First floor sheathing starts at floor_start position (from config)
    # Use same calculation as floor_params to ensure exact alignment
    first_floor_start_x_ft = (lot_x_ft - floor_width_ft) / 2.0  # Same as floor_params["floor_start_x_ft"]
    first_floor_start_y_ft = front_setback_ft + y_spacing_ft  # Same as floor_params["floor_start_y_ft"]
    first_floor_start_x_in = first_floor_start_x_ft * 12.0
    first_floor_start_y_in = first_floor_start_y_ft * 12.0

    # Sheathing X bounds: inside the deck exclusion zones
    sheathing_x_min_in = first_floor_start_x_in + side_deck_width_in
    sheathing_x_max_in = first_floor_start_x_in + (floor_width_ft * 12.0) - side_deck_width_in

    # Sheathing Y bounds: from first floor start to first floor start + depth
    sheathing_y_min_in = first_floor_start_y_in  # South edge of first floor sheathing
    sheathing_y_max_in = first_floor_start_y_in + (floor_depth_ft * 12.0)  # North edge of first floor sheathing

    App.Console.PrintMessage(f"[Build_950Surf]   First floor sheathing: X=[{sheathing_x_min_in:.2f}, {sheathing_x_max_in:.2f}], Y=[{sheathing_y_min_in:.2f}, {sheathing_y_max_in:.2f}]\n")

    # ============================================================
    # Define perimeter (outer bounds of entire deck including overhang)
    # ============================================================
    perimeter = {
        "x_min_in": deck_frame_x_min_in,  # Overhang applied inside create_unified_deck_surface
        "x_max_in": deck_frame_x_max_in,
        "y_min_in": deck_frame_y_min_in,
        "y_max_in": deck_frame_y_max_in,
    }

    # ============================================================
    # Define zones (areas with same board direction)
    # ============================================================
    # Board direction is perpendicular to joist direction:
    # - NS joists (front/rear decks) -> EW boards
    # - EW joists (side decks/floor) -> NS boards

    # Calculate first joist offset for EW boards (front/rear decks)
    # Front deck joists (running NS) are at X positions:
    #   - Left rim center: deck_frame_x_min + 0.75"
    #   - First interior joist: deck_frame_x_min + 15.25" (rim + 14.5" first_spacing)
    #   - Subsequent joists: 16" O.C. after that
    # Field boards start after picture frame edge: deck_frame_x_min + 5.5" + 0.125" = +5.625"
    # First interior joist relative to field start: 15.25" - 5.625" = 9.625"
    deck_board_width_in = 5.5  # 5/4x6 deck board width
    deck_board_gap_in = 0.125  # 1/8" gap
    joist_first_spacing_in = 14.5  # First joist at 14.5" from rim (for sheathing alignment)
    joist_thick_in = 1.5  # 2x lumber thickness

    # Picture frame edge takes: deck_board_width + gap = 5.625"
    frame_edge_offset = deck_board_width_in + deck_board_gap_in  # 5.625"
    # First interior joist from deck origin: rim_center + first_spacing = 0.75 + 14.5 = 15.25"
    first_interior_joist_from_origin = (joist_thick_in / 2.0) + joist_first_spacing_in  # 15.25"
    # First joist offset from field board start (EW boards after picture frame edge)
    ew_first_joist_offset_in = first_interior_joist_from_origin - frame_edge_offset  # 9.625"

    # For NS boards on side decks:
    # Side deck zones start at sheathing_y_min (floor module Y origin)
    # Floor joist modules have front rim center at origin + 0.75"
    # NS field boards need to land on floor joists (running EW)
    # First joist from zone start = rim center = 0.75"
    ns_first_joist_offset_in = joist_thick_in / 2.0  # 0.75"

    # ============================================================
    # Picture frame joist offsets (for edge board splices)
    # ============================================================
    # Picture frame boards extend 1" beyond framing (DECK_OVERHANG_IN in deck_assemblies)
    # So we need to add that offset when calculating distance to first joist
    deck_overhang_in = 1.0  # Must match DECK_OVERHANG_IN in deck_assemblies.py

    # EW picture frame boards (front/back edges): splice on NS joists
    # Frame starts at deck_frame_x_min - 1" (overhang)
    # First interior joist center at deck_frame_x_min + 15.25"
    # Offset from frame start to first interior joist = 15.25" + 1.0" = 16.25"
    pf_ew_first_joist_offset_in = first_interior_joist_from_origin + deck_overhang_in  # 16.25"

    # NS picture frame boards (left/right edges): splice on EW joists
    # Frame starts at deck_frame_y_min - 1" (overhang)
    # Front deck NS joists at: y_min + 0.75" (rim), y_min + 15.25" (first interior), etc.
    # Offset from frame start to rim joist = 0.75" + 1.0" = 1.75"
    pf_ns_first_joist_offset_in = (joist_thick_in / 2.0) + deck_overhang_in  # 1.75"

    zones = [
        # Front deck: full width, 12' deep, EW boards
        {
            "name": "Front_Deck",
            "x_min_in": deck_frame_x_min_in,
            "x_max_in": deck_frame_x_max_in,
            "y_min_in": deck_frame_y_min_in,
            "y_max_in": sheathing_y_min_in,  # Up to sheathing south edge
            "joist_direction": "NS",  # Joists run north-south
            "seam_positions_in": [72.0],  # Seam at 6' from front (legacy, ignored)
            "first_joist_offset_in": ew_first_joist_offset_in,  # Align splices with actual joists
        },
        # Left side deck: narrow strip along west side, NS boards
        {
            "name": "Left_Side_Deck",
            "x_min_in": deck_frame_x_min_in,
            "x_max_in": sheathing_x_min_in,  # Up to sheathing west edge
            "y_min_in": sheathing_y_min_in,  # Start at front deck north edge
            "y_max_in": sheathing_y_max_in,  # End at rear deck south edge
            "joist_direction": "EW",  # Joists run east-west (floor joists)
            "first_joist_offset_in": ns_first_joist_offset_in,  # Align with floor joists
        },
        # Right side deck: narrow strip along east side, NS boards
        # ns_layout_direction: "right_to_left" puts rip board against house (west side)
        {
            "name": "Right_Side_Deck",
            "x_min_in": sheathing_x_max_in,  # Start at sheathing east edge
            "x_max_in": deck_frame_x_max_in,
            "y_min_in": sheathing_y_min_in,
            "y_max_in": sheathing_y_max_in,
            "joist_direction": "EW",  # Joists run east-west
            "ns_layout_direction": "right_to_left",  # Start from picture frame, rip against house
            "first_joist_offset_in": ns_first_joist_offset_in,  # Align with floor joists
        },
        # Rear deck: full width, 4' deep, EW boards
        {
            "name": "Rear_Deck",
            "x_min_in": deck_frame_x_min_in,
            "x_max_in": deck_frame_x_max_in,
            "y_min_in": sheathing_y_max_in,  # Start at sheathing north edge
            "y_max_in": deck_frame_y_max_in,
            "joist_direction": "NS",  # Joists run north-south
            "first_joist_offset_in": ew_first_joist_offset_in,  # Same offset as front deck
        },
    ]

    App.Console.PrintMessage(f"[Build_950Surf]   Zones defined: {[z['name'] for z in zones]}\n")

    # ============================================================
    # Create unified deck surface
    # ============================================================
    unified_deck = da.create_unified_deck_surface(
        doc,
        catalog_rows,
        perimeter=perimeter,
        zones=zones,
        assembly_name="Unified_Deck_Surface",
        z_base=deck_z_base_in,
        supplier="lowes",
        joist_depth_in=FIRST_FLOOR["joist_depth_in"],
        picture_frame_ew_joist_offset=pf_ew_first_joist_offset_in,
        picture_frame_ns_joist_offset=pf_ns_first_joist_offset_in,
    )

    deck_surface_assemblies = [unified_deck]

    # NOTE: Perpendicular deck boards over stair opening removed - stairs now in front deck area
    # The stair opening will be framed as part of the front deck joist module (future implementation)

    # Create Deck_Surface group
    deck_surface_grp = bc.create_group(doc, "Deck_Surface")
    bc.add_to_group(deck_surface_grp, deck_surface_assemblies)

    App.Console.PrintMessage(f"[Build_950Surf] Unified deck surface complete ({len(deck_surface_assemblies)} assemblies).\n")
else:
    App.Console.PrintMessage("[Build_950Surf] Deck surface skipped (disabled in BUILD config)\n")

# ============================================================
# SECTION 8D-2: DECK RAILINGS (posts, rails, balusters)
# ============================================================
# Deck railings are installed after deck surface is complete
# Posts extend from bottom of joists (for strength) to 48" above deck surface
# Posts are positioned inside rim joists, directly against rim inside face
# Blocking will be added later to secure posts (connects joist-to-joist, hugging post)

if BUILD.get("include_deck_railings", False):
    App.Console.PrintMessage("[Build_950Surf] Building deck railings...\n")

    # Import railing module
    import railing_assemblies as ra
    importlib.reload(ra)

    # Calculate deck surface Z position (top of deck boards)
    # deck_z_base_in = joist bottom (foundation level)
    # Deck boards sit ON TOP of joists, so:
    # deck surface top = joist bottom + joist depth + deck board thickness
    #
    # Get deck board thickness from catalog (same source as deck_assemblies uses)
    deck_board_label = "deckboard_5_4x6x192_PT"  # Same as da.DECK_BOARD_LABEL
    deck_board_row = lc.find_stock(catalog_rows, deck_board_label)
    if not deck_board_row:
        raise ValueError(f"Deck board '{deck_board_label}' not found in catalog")
    deck_board_thick_in = float(deck_board_row["actual_thickness_in"])  # 5/4 actual = 1.0"
    joist_depth_in = FIRST_FLOOR["joist_depth_in"]  # 2x12 actual = 11.25"
    deck_surface_top_z_in = deck_z_base_in + joist_depth_in + deck_board_thick_in

    # ============================================================
    # DECK RAILING STRATEGY - Continuous Perimeter with L-Shaped Corners
    # ============================================================
    #
    # The deck forms an L-shape around the house footprint:
    # - Front deck: full width, extends south from house
    # - Side decks: narrow strips along east/west house walls
    # - Rear deck: full width, extends north from house
    #
    # SAFETY-CRITICAL: IRC R312.1.3 requires max 4" gaps (sphere rule)
    # Railings must form a continuous barrier with no gaps > 4" where a
    # baby could crawl through and fall.
    #
    # The railings are organized into sections that connect at corners:
    # 1. Front deck: south edge (full), west edge (to sheathing), east edge (to sheathing)
    # 2. Side decks: west/east outer edges only (from sheathing_y_min to sheathing_y_max)
    # 3. Rear deck: north edge (full), west edge (from sheathing), east edge (from sheathing)
    #
    # Corner connections (no gaps):
    # - SW corner: Front west railing continues into left side west railing
    # - SE corner: Front east railing continues into right side east railing
    # - NW corner: Left side west railing continues into rear west railing
    # - NE corner: Right side east railing continues into rear east railing
    #
    # NOTE: Elevator opening on east side will be handled separately once elevator is enabled

    # Front deck: South edge (continuous), plus west/east sections to house wall
    # The south edge runs full width; east/west edges only run to sheathing line
    front_deck_railing_perimeter = {
        "x_min_in": deck_frame_x_min_in,
        "x_max_in": deck_frame_x_max_in,
        "y_min_in": deck_frame_y_min_in,
        "y_max_in": sheathing_y_min_in,  # Up to where sheathing starts (house wall)
    }

    # =========================================================================
    # ELEVATOR OPENING: Remove railing section(s) and center elevator in opening
    # =========================================================================
    front_deck_gate_openings = []

    if BUILD.get("include_elevator", False):
        # Get elevator position and size from config
        elev_x_ft = ELEVATOR.get("elevator_x_ft", 42.0)
        elev_width_ft = ELEVATOR.get("platform_width_ft", 4.0)
        elev_x_in = elev_x_ft * 12.0
        elev_width_in = elev_width_ft * 12.0

        # Calculate post positions along south edge (must match railing module logic!)
        # Railing module uses RUN boundaries at rim inside face (perimeter - rim_thick)
        # Then places posts with centers at run_boundary + post_thick/2
        railing_rim_thick_in = 1.5  # 2x rim joist actual thickness
        railing_post_thick_in = 3.5  # 4x4 PT actual

        # Run boundaries: at rim inside faces (where posts can start/end)
        south_run_x_start_in = deck_frame_x_min_in + railing_rim_thick_in  # Run start at west rim inside face
        south_run_x_end_in = deck_frame_x_max_in - railing_rim_thick_in    # Run end at east rim inside face
        south_run_length_in = south_run_x_end_in - south_run_x_start_in

        railing_max_spacing_in = 48.0  # IRC R507.9.1 max
        num_spans = int((south_run_length_in - railing_post_thick_in) / railing_max_spacing_in) + 1
        actual_spacing_in = (south_run_length_in - railing_post_thick_in) / num_spans

        # Find which section(s) the elevator overlaps
        elev_west_in = elev_x_in - elev_width_in / 2.0
        elev_east_in = elev_x_in + elev_width_in / 2.0

        # Post positions (absolute X coordinates, matching railing module calculation)
        # _calculate_post_positions places first post at run_start + post_thick/2
        # So first post center is at south_run_x_start_in + post_thick/2
        post_positions_in = []
        for i in range(num_spans + 1):
            post_x = south_run_x_start_in + railing_post_thick_in / 2.0 + i * actual_spacing_in
            post_positions_in.append(post_x)

        # Find sections that the elevator overlaps (section = gap between adjacent posts)
        overlapped_sections = []
        for i in range(len(post_positions_in) - 1):
            section_west = post_positions_in[i]
            section_east = post_positions_in[i + 1]
            # Check if elevator overlaps this section
            if elev_west_in < section_east and elev_east_in > section_west:
                overlapped_sections.append(i)

        if overlapped_sections:
            # Create opening that spans all overlapped sections
            # opening_west_post: post at WEST edge of opening (stays, railing attaches to it)
            # opening_east_post: post at EAST edge of opening (stays, railing attaches to it)
            first_section = overlapped_sections[0]
            last_section = overlapped_sections[-1]
            opening_west_post_center = post_positions_in[first_section]
            opening_east_post_center = post_positions_in[last_section + 1]

            # Gate opening starts at west post east edge, ends at east post west edge
            # This allows segment 1 to end with west post, segment 2 to start with east post
            half_post = railing_post_thick_in / 2.0
            opening_start_in = (opening_west_post_center + half_post) - south_run_x_start_in
            opening_end_in = (opening_east_post_center - half_post) - south_run_x_start_in
            opening_width_in = opening_end_in - opening_start_in

            front_deck_gate_openings.append({
                "side": "south",
                "start_in": opening_start_in,
                "width_in": opening_width_in,
            })

            # Align elevator to WEST edge of opening (setback constraint: ground elements can't exceed offset)
            # Elevator SW post should align with opening west railing post
            # Elevator center = opening_west_post_center + platform_width/2
            new_elev_x_in = opening_west_post_center + elev_width_in / 2.0
            new_elev_x_ft = new_elev_x_in / 12.0

            App.Console.PrintMessage(f"[Build_950Surf]   Elevator opening: sections {first_section + 1}-{last_section + 1} removed\n")
            App.Console.PrintMessage(f"[Build_950Surf]   Opening: between post {first_section + 1} (X={opening_west_post_center / 12.0:.2f}') and post {last_section + 2} (X={opening_east_post_center / 12.0:.2f}')\n")

            # Move elevator to west edge of opening
            if abs(new_elev_x_ft - elev_x_ft) > 0.01:
                App.Console.PrintMessage(f"[Build_950Surf]   Elevator moved: X={elev_x_ft:.2f}' -> {new_elev_x_ft:.2f}' (aligned to west edge)\n")
                # Update elevator position in document
                if "elevator_grp" in dir() and elevator_grp:
                    # Move the elevator group to the new position
                    dx_mm = (new_elev_x_ft - elev_x_ft) * 12.0 * 25.4
                    for obj in elevator_grp.Group:
                        obj.Placement.Base.x += dx_mm

            # Calculate east-side gap between elevator SE post and deck railing post
            # Elevator SE post X = new_elev_x + platform_width/2 = opening_west_post_center + platform_width
            elevator_se_post_x_in = new_elev_x_in + elev_width_in / 2.0
            east_gap_in = opening_east_post_center - elevator_se_post_x_in

            # Store for east-side railing section (added after main railing creation)
            elevator_east_railing_config = {
                "deck_post_x_in": opening_east_post_center,
                "elevator_se_x_in": elevator_se_post_x_in,
                "gap_in": east_gap_in,
                "deck_surface_z_in": deck_surface_top_z_in,
                "deck_y_min_in": deck_frame_y_min_in,
            }
            App.Console.PrintMessage(f"[Build_950Surf]   East-side gap: {east_gap_in:.1f}\" ({east_gap_in / 12.0:.2f}') between elevator SE post and deck post\n")

    front_deck_railings = ra.create_deck_railings(
        doc,
        catalog_rows,
        perimeter=front_deck_railing_perimeter,
        deck_surface_z_in=deck_surface_top_z_in,
        assembly_name="Front_Deck_Railings",
        supplier="lowes",
        exclude_sides=["north"],  # No railing against house
        gate_openings=front_deck_gate_openings,
        post_height_above_deck_in=48.0,  # 48" above deck surface
        joist_depth_in=joist_depth_in,
        deck_board_thick_in=deck_board_thick_in,
    )

    # =========================================================================
    # ELEVATOR OPENING RAILING: Complete railing at east edge of elevator opening
    # =========================================================================
    # Add a complete railing section (post, top rail, bottom rail, balusters)
    # between the elevator SE post and the deck railing post
    if BUILD.get("include_elevator", False) and "elevator_east_railing_config" in dir():
        config = elevator_east_railing_config
        gap_in = config["gap_in"]  # X gap between elevator SE post and deck post

        # Only add railing if there's a meaningful gap
        if gap_in > 6.0:
            deck_post_x_in = config["deck_post_x_in"]  # East edge post X (center)
            elevator_se_x_in = config["elevator_se_x_in"]  # Elevator SE post X (center)
            deck_surface_z_in = config["deck_surface_z_in"]
            deck_y_min_in = config["deck_y_min_in"]

            # Railing dimensions (match deck railing module)
            railing_rim_thick_in = 1.5
            post_thick_in = 3.5  # 4x4 PT actual
            post_height_in = 48.0  # 48" above deck
            rail_thick_in = 1.5  # 2x4 rail thickness
            rail_width_in = 3.5  # 2x4 rail width
            baluster_thick_in = 1.5  # 2x2 baluster
            baluster_spacing_max_in = 4.0  # IRC R312.1.3: max 4" sphere opening

            # Y position: at deck frame south edge (outer face of rim joist)
            # This aligns with where the elevator opening is and where balusters should fill
            railing_y_in = deck_y_min_in

            # Railing runs E-W from elevator SE post to deck post
            # Start X: elevator SE post east edge
            # End X: deck post west edge
            half_post = post_thick_in / 2.0
            start_x_in = elevator_se_x_in + half_post  # Elevator SE post east edge
            end_x_in = deck_post_x_in - half_post  # Deck post west edge
            rail_length_in = end_x_in - start_x_in

            App.Console.PrintMessage(f"[Build_950Surf]   Creating elevator opening railing: {rail_length_in:.1f}\" long (X={start_x_in / 12.0:.2f}' to {end_x_in / 12.0:.2f}')\n")

            # Create assembly for elevator opening railing
            import Part as ElevPart
            elev_railing_parts = []

            # Z positions
            post_base_z_in = deck_surface_z_in
            bottom_rail_z_in = deck_surface_z_in + 3.0  # 3" above deck
            top_rail_z_in = deck_surface_z_in + post_height_in - rail_width_in  # Below post top
            baluster_base_z_in = bottom_rail_z_in + rail_width_in  # On top of bottom rail
            baluster_height_in = top_rail_z_in - baluster_base_z_in  # Between rails

            # Helper to safely set color
            def safe_set_color(obj, color):
                try:
                    if hasattr(obj, "ViewObject") and obj.ViewObject:
                        obj.ViewObject.ShapeColor = color
                except Exception:
                    pass

            # PT wood color
            pt_color = (0.55, 0.45, 0.35)

            # 1. Transition post at elevator SE (4x4 PT on deck surface)
            transition_post = doc.addObject("Part::Box", "Elevator_Opening_Post")
            transition_post.Length = bc.inch(post_thick_in)
            transition_post.Width = bc.inch(post_thick_in)
            transition_post.Height = bc.inch(post_height_in)
            transition_post.Placement.Base = App.Vector(
                bc.inch(elevator_se_x_in - half_post),
                bc.inch(railing_y_in - half_post),
                bc.inch(post_base_z_in),
            )
            safe_set_color(transition_post, pt_color)
            elev_railing_parts.append(transition_post)

            # 2. Top rail (2x4 PT, runs E-W)
            top_rail = doc.addObject("Part::Box", "Elevator_Opening_Top_Rail")
            top_rail.Length = bc.inch(rail_length_in)
            top_rail.Width = bc.inch(rail_thick_in)
            top_rail.Height = bc.inch(rail_width_in)
            top_rail.Placement.Base = App.Vector(
                bc.inch(start_x_in),
                bc.inch(railing_y_in - rail_thick_in / 2.0),
                bc.inch(top_rail_z_in),
            )
            safe_set_color(top_rail, pt_color)
            elev_railing_parts.append(top_rail)

            # 3. Bottom rail (2x4 PT, runs E-W)
            bottom_rail = doc.addObject("Part::Box", "Elevator_Opening_Bottom_Rail")
            bottom_rail.Length = bc.inch(rail_length_in)
            bottom_rail.Width = bc.inch(rail_thick_in)
            bottom_rail.Height = bc.inch(rail_width_in)
            bottom_rail.Placement.Base = App.Vector(
                bc.inch(start_x_in),
                bc.inch(railing_y_in - rail_thick_in / 2.0),
                bc.inch(bottom_rail_z_in),
            )
            safe_set_color(bottom_rail, pt_color)
            elev_railing_parts.append(bottom_rail)

            # 4. Balusters (2x2 PT, spaced to meet 4" sphere rule)
            # Calculate number of balusters needed
            # Available space = rail_length_in
            # Each baluster takes baluster_thick_in, gaps must be <= 4"
            # n balusters create (n+1) gaps: rail_length = n*baluster_thick + (n+1)*gap
            # For gap <= 4": n >= (rail_length - 4) / (baluster_thick + 4)
            import math
            num_balusters = max(1, int(math.ceil((rail_length_in - baluster_spacing_max_in) / (baluster_thick_in + baluster_spacing_max_in))))
            # Actual gap with n balusters
            total_baluster_width = num_balusters * baluster_thick_in
            total_gap_space = rail_length_in - total_baluster_width
            num_gaps = num_balusters + 1
            actual_gap_in = total_gap_space / num_gaps

            for i in range(num_balusters):
                # Baluster center X = start_x + gap + (i * (baluster + gap)) + baluster/2
                bal_center_x_in = start_x_in + actual_gap_in + i * (baluster_thick_in + actual_gap_in) + baluster_thick_in / 2.0

                baluster = doc.addObject("Part::Box", f"Elevator_Opening_Baluster_{i+1}")
                baluster.Length = bc.inch(baluster_thick_in)
                baluster.Width = bc.inch(baluster_thick_in)
                baluster.Height = bc.inch(baluster_height_in)
                baluster.Placement.Base = App.Vector(
                    bc.inch(bal_center_x_in - baluster_thick_in / 2.0),
                    bc.inch(railing_y_in - baluster_thick_in / 2.0),
                    bc.inch(baluster_base_z_in),
                )
                safe_set_color(baluster, pt_color)
                elev_railing_parts.append(baluster)

            # Create assembly
            elev_opening_assembly = doc.addObject("App::Part", "Elevator_Opening_Railing")
            elev_opening_assembly.Label = "Elevator_Opening_Railing"
            for obj in elev_railing_parts:
                elev_opening_assembly.addObject(obj)

            App.Console.PrintMessage(f"[Build_950Surf]   Created elevator opening railing: 1 post, 2 rails, {num_balusters} balusters (gap: {actual_gap_in:.2f}\")\n")
        else:
            App.Console.PrintMessage(f"[Build_950Surf]   Elevator east gap too small ({gap_in:.1f}\"), no railing needed\n")

    # Rear deck: North edge (continuous), plus west/east sections from house wall
    rear_deck_railing_perimeter = {
        "x_min_in": deck_frame_x_min_in,
        "x_max_in": deck_frame_x_max_in,
        "y_min_in": sheathing_y_max_in,  # Start where sheathing ends (house wall)
        "y_max_in": deck_frame_y_max_in,
    }

    rear_deck_railings = ra.create_deck_railings(
        doc,
        catalog_rows,
        perimeter=rear_deck_railing_perimeter,
        deck_surface_z_in=deck_surface_top_z_in,
        assembly_name="Rear_Deck_Railings",
        supplier="lowes",
        exclude_sides=["south"],  # No railing against house
        post_height_above_deck_in=48.0,
        joist_depth_in=joist_depth_in,
        deck_board_thick_in=deck_board_thick_in,
    )

    # Side deck railings: These ONLY cover the outer edges (west for left, east for right)
    # along the house wall section. The north/south connections are provided by
    # the front/rear deck west/east railings extending to sheathing line.
    #
    # Left side deck: west edge only (continuous from front corner to rear corner)
    left_side_deck_railing_perimeter = {
        "x_min_in": deck_frame_x_min_in,
        "x_max_in": sheathing_x_min_in,  # Up to house wall
        "y_min_in": sheathing_y_min_in,
        "y_max_in": sheathing_y_max_in,
    }

    left_side_deck_railings = ra.create_deck_railings(
        doc,
        catalog_rows,
        perimeter=left_side_deck_railing_perimeter,
        deck_surface_z_in=deck_surface_top_z_in,
        assembly_name="Left_Side_Deck_Railings",
        supplier="lowes",
        exclude_sides=["east", "north", "south"],  # Only west edge
        post_height_above_deck_in=48.0,
        joist_depth_in=joist_depth_in,
        deck_board_thick_in=deck_board_thick_in,
    )

    # Right side deck: east edge only
    right_side_deck_railing_perimeter = {
        "x_min_in": sheathing_x_max_in,  # Start at house wall
        "x_max_in": deck_frame_x_max_in,
        "y_min_in": sheathing_y_min_in,
        "y_max_in": sheathing_y_max_in,
    }

    right_side_deck_railings = ra.create_deck_railings(
        doc,
        catalog_rows,
        perimeter=right_side_deck_railing_perimeter,
        deck_surface_z_in=deck_surface_top_z_in,
        assembly_name="Right_Side_Deck_Railings",
        supplier="lowes",
        exclude_sides=["west", "north", "south"],  # Only east edge
        post_height_above_deck_in=48.0,
        joist_depth_in=joist_depth_in,
        deck_board_thick_in=deck_board_thick_in,
    )

    # ============================================================
    # CORNER TRANSITION RAILINGS - Fill gaps at L-shaped corners
    # ============================================================
    # At each corner where front/rear deck meets side deck, there's a gap
    # between railing sections. The gap is approximately 2 * post_inset = 6.5"
    # which exceeds the IRC R312.1.3 4" sphere rule.
    #
    # The existing corner deduplication logic ensures:
    # - E-W sides (front/rear deck) OWN their corner posts
    # - N-S sides (side decks) SKIP corner posts where E-W sides exist
    #
    # This means the existing posts are positioned correctly, but there's a gap
    # in the RAILS between the two railing assemblies at each corner.
    #
    # The gap geometry:
    # - Front deck west railing ends with post at y = front_perimeter_y_max - post_inset
    #   where front_perimeter_y_max = sheathing_y_min_in
    #   So post Y = sheathing_y_min_in - 3.25"
    #
    # - Side deck west railing starts with post at y = side_perimeter_y_min + post_inset
    #   where side_perimeter_y_min = sheathing_y_min_in
    #   So post Y = sheathing_y_min_in + 3.25"
    #
    # The gap between posts = 6.5" (violates 4" sphere rule)
    #
    # FIX: Create short transition rail sections that span from post face to post face
    # These rails run parallel to Y axis (N-S direction) and connect the corner posts.
    # We create rails directly (not using create_railing_section since we don't need posts).

    import Part
    corner_railings = []
    rim_thick = 1.5  # 2x lumber rim joist thickness
    post_thick = 3.5  # 4x4 post thickness
    post_inset = rim_thick + post_thick / 2.0  # 3.25" from perimeter edge to post center
    rail_thick = 1.5  # 2x4 rail thickness
    rail_width = 3.5  # 2x4 rail width

    # Post base and heights (same as main railings)
    post_base_z_in = deck_surface_top_z_in - deck_board_thick_in - joist_depth_in
    post_height_above_deck_in = 48.0
    post_height_in = (deck_surface_top_z_in - post_base_z_in) + post_height_above_deck_in

    # Rail Z positions
    top_rail_z = post_base_z_in + post_height_in - rail_thick
    bottom_rail_z = deck_surface_top_z_in + 3.5  # 3.5" above deck (same as BOTTOM_RAIL_HEIGHT_ABOVE_DECK_IN)

    # Gap span: from front post face to side post face
    # Front post north face is at: sheathing_y_min_in - post_inset + post_thick/2 = sheathing_y_min_in - 1.5"
    # Side post south face is at: sheathing_y_min_in + post_inset - post_thick/2 = sheathing_y_min_in + 1.5"
    # Gap span = 3.0" (from front post north face to side post south face)
    front_post_north_face_y = sheathing_y_min_in - post_inset + post_thick / 2.0  # -1.5" from sheathing
    side_post_south_face_y = sheathing_y_min_in + post_inset - post_thick / 2.0   # +1.5" from sheathing
    gap_span_south = side_post_south_face_y - front_post_north_face_y  # 3.0"

    # Similarly for rear transition (side deck north end to rear deck south end)
    side_post_north_face_y = sheathing_y_max_in - post_inset + post_thick / 2.0  # -1.5" from sheathing
    rear_post_south_face_y = sheathing_y_max_in + post_inset - post_thick / 2.0  # +1.5" from sheathing
    gap_span_north = rear_post_south_face_y - side_post_north_face_y  # 3.0"

    # Helper to create transition rails
    def create_corner_transition_rails(x_center_in, y_start_in, y_end_in, corner_name):
        """Create top and bottom rails for corner transition."""
        rails = []
        span_length = y_end_in - y_start_in

        if span_length < 0.5:
            App.Console.PrintWarning(f"[railing] {corner_name} transition too short ({span_length:.1f}in), skipping\n")
            return rails

        # Top rail (runs N-S)
        top_rail_name = f"{corner_name}_TopRail"
        top_rail = doc.addObject("Part::Feature", top_rail_name)
        top_rail.Shape = Part.makeBox(
            lc.inch(rail_width),
            lc.inch(span_length),
            lc.inch(rail_thick),
        )
        top_rail.Placement.Base = App.Vector(
            lc.inch(x_center_in - rail_width / 2.0),
            lc.inch(y_start_in),
            lc.inch(top_rail_z),
        )
        rails.append(top_rail)

        # Bottom rail
        bottom_rail_name = f"{corner_name}_BottomRail"
        bottom_rail = doc.addObject("Part::Feature", bottom_rail_name)
        bottom_rail.Shape = Part.makeBox(
            lc.inch(rail_width),
            lc.inch(span_length),
            lc.inch(rail_thick),
        )
        bottom_rail.Placement.Base = App.Vector(
            lc.inch(x_center_in - rail_width / 2.0),
            lc.inch(y_start_in),
            lc.inch(bottom_rail_z),
        )
        rails.append(bottom_rail)

        # Balusters in gap (if gap > baluster thickness)
        baluster_thick = 1.5  # 2x2
        baluster_width = 1.5
        baluster_z_bottom = bottom_rail_z + rail_thick
        baluster_z_top = top_rail_z
        baluster_height = baluster_z_top - baluster_z_bottom

        if baluster_height > 1.0 and span_length > baluster_thick:
            # Center a baluster in the gap
            baluster_name = f"{corner_name}_Baluster_1"
            bal = doc.addObject("Part::Feature", baluster_name)
            bal.Shape = Part.makeBox(
                lc.inch(baluster_thick),
                lc.inch(baluster_width),
                lc.inch(baluster_height),
            )
            bal.Placement.Base = App.Vector(
                lc.inch(x_center_in - baluster_thick / 2.0),
                lc.inch(y_start_in + (span_length - baluster_width) / 2.0),
                lc.inch(baluster_z_bottom),
            )
            rails.append(bal)

        return rails

    # SW Corner: west edge, front deck to side deck transition
    sw_x = deck_frame_x_min_in + post_inset  # West edge post centerline X
    sw_rails = create_corner_transition_rails(sw_x, front_post_north_face_y, side_post_south_face_y, "SW_Corner")
    corner_railings.extend(sw_rails)

    # SE Corner: east edge, front deck to side deck transition
    se_x = deck_frame_x_max_in - post_inset  # East edge post centerline X
    se_rails = create_corner_transition_rails(se_x, front_post_north_face_y, side_post_south_face_y, "SE_Corner")
    corner_railings.extend(se_rails)

    # NW Corner: west edge, side deck to rear deck transition
    nw_rails = create_corner_transition_rails(sw_x, side_post_north_face_y, rear_post_south_face_y, "NW_Corner")
    corner_railings.extend(nw_rails)

    # NE Corner: east edge, side deck to rear deck transition
    ne_rails = create_corner_transition_rails(se_x, side_post_north_face_y, rear_post_south_face_y, "NE_Corner")
    corner_railings.extend(ne_rails)

    # Create corner transition assembly
    corner_transition_assembly = doc.addObject("App::Part", "Corner_Transition_Railings")
    corner_transition_assembly.Label = "Corner_Transition_Railings"
    for obj in corner_railings:
        corner_transition_assembly.addObject(obj)

    App.Console.PrintMessage(f"[railing] (done) Corner transitions complete: 4 corners, {len(corner_railings)} components\n")

    # Create Deck_Railings group
    deck_railing_grp = bc.create_group(doc, "Deck_Railings")
    bc.add_to_group(deck_railing_grp, [front_deck_railings, rear_deck_railings, left_side_deck_railings, right_side_deck_railings, corner_transition_assembly])

    App.Console.PrintMessage("[Build_950Surf] Deck railings complete.\n")
else:
    App.Console.PrintMessage("[Build_950Surf] Deck railings skipped (disabled in BUILD config)\n")

# ============================================================
# SECTION 8E: SECOND FLOOR JOIST MODULES (20' LVL rims x 12' 2x12 joists)
# ============================================================
# Second floor sits on top of first floor walls
# Layout: 2 columns x 4 rows = 8 modules = 40' x 48'
# Module dimensions: 20' wide (E-W) x 12' deep (N-S)
# Materials: 20' LVL rims (E-W), 12' 2x12 joists (N-S) at 16" OC

if BUILD.get("include_second_floor", False):
    App.Console.PrintMessage("[Build_950Surf] === SECOND FLOOR ===\n")
    App.Console.PrintMessage("[Build_950Surf] Building second floor joist modules (2x4 grid = 8 modules)...\n")

    # Import parts module (already in sys.path via _macros_dir)
    import lumber_common as lc
    import parts
    importlib.reload(parts)

    # Load catalog for second floor assemblies
    catalog_path = os.path.join(_design_house_root, "lumber", "lumber_catalog.csv")
    catalog_rows = lc.load_catalog(catalog_path)

    # Calculate second floor Z position
    # Base Z = first floor Z + joist depth + sheathing + wall assembly height
    # Wall assembly height = plate (1.5") + studs (104.625") + plate (1.5") + plate (1.5") = 109.125"
    # This is the TOP of the double top plate (where second floor joists sit)
    first_floor_z_in = above_grade_ft * 12.0  # First floor joist base
    joist_depth_in = FIRST_FLOOR["joist_depth_in"]  # 11.25"
    sheathing_thickness_in = FIRST_FLOOR["sheathing_thickness_in"]  # 0.75"
    # Actual wall assembly height: bottom plate + precut studs + top plate + double top plate
    plate_thick_in = 1.5  # 2x4 plate thickness
    stud_length_in = 104.625  # Precut stud length (for 8' ceiling)
    wall_assembly_height_in = plate_thick_in + stud_length_in + plate_thick_in + plate_thick_in  # 109.125"
    second_floor_z_in = first_floor_z_in + joist_depth_in + sheathing_thickness_in + wall_assembly_height_in
    second_floor_z_ft = second_floor_z_in / 12.0

    App.Console.PrintMessage(f"[Build_950Surf]   Second floor joist bottom Z = {second_floor_z_ft:.2f}' ({second_floor_z_in:.2f}\")\n")

    # Second floor positioning from config
    second_floor_start_x_ft = SECOND_FLOOR["start_x_ft"]  # 5.0' (left setback)
    second_floor_start_y_ft = SECOND_FLOOR["start_y_ft"]  # 20.0' (front setback)

    # Module dimensions from config
    module_width_ft = SECOND_FLOOR["module_width_ft"]  # 20' (nominal, used for stock selection)
    module_depth_ft = SECOND_FLOOR["module_depth_ft"]  # 12'
    grid_columns = SECOND_FLOOR["grid_columns"]  # 2
    grid_rows = SECOND_FLOOR["grid_rows"]  # 4

    # LVL rim thickness for positioning calculations
    rim_thick_in = SECOND_FLOOR["rim_thickness_in"]  # 1.75"

    # Calculate target floor dimensions to match first floor walls
    # First floor sheathing spans from left wall to right wall = 40'
    # This is derived from: lot_width - left_setback - right_setback = 50 - 5 - 5 = 40'
    # We want 2 modules x target_module_width = 40'
    target_floor_width_ft = LOT["width_ft"] - LOT["left_setback_ft"] - LOT["right_setback_ft"]  # 40'
    target_floor_depth_ft = module_depth_ft * grid_rows  # 12' x 4 = 48'
    target_floor_depth_in = target_floor_depth_ft * 12.0  # 576"

    # Calculate target module width (including side rims) - NO MAGIC NUMBERS
    # target_module_width = target_floor_width / grid_columns
    target_module_width_in = (target_floor_width_ft * 12.0) / grid_columns  # 240" (20')

    # Module depth: Full-length rows use full joist stock (no target_module_depth_in)
    # Geometry: front LVL + joist_run (2x12s run parallel between LVL rims) + back LVL
    # Module depth = rim_thick + joist_run + rim_thick
    # With full joists: = 1.75 + 144 + 1.75 = 147.5"
    joist_stock_length_in = 144.0  # 12' joists
    full_module_depth_in = rim_thick_in + joist_stock_length_in + rim_thick_in  # 1.75 + 144 + 1.75 = 147.5"

    # Last row may need shorter joists to fit 48' total
    # First (grid_rows - 1) rows use full joists, last row fills remaining space
    full_rows = grid_rows - 1
    remaining_depth_in = target_floor_depth_in - (full_rows * full_module_depth_in)  # 576 - 3*147.5 = 133.5"

    App.Console.PrintMessage(
        f"[Build_950Surf]   Target floor: {target_floor_width_ft:.0f}' x {target_floor_depth_ft:.0f}' ({target_floor_depth_in:.0f}\")\n"
    )
    App.Console.PrintMessage(
        f"[Build_950Surf]   Rows 1-{full_rows}: full joists ({joist_stock_length_in:.0f}\"), module depth = {full_module_depth_in:.2f}\"\n"
    )
    App.Console.PrintMessage(
        f"[Build_950Surf]   Row {grid_rows}: remaining depth = {remaining_depth_in:.2f}\" "
        f"(joist run = {remaining_depth_in - 2*rim_thick_in:.2f}\")\n"
    )

    second_floor_assemblies = []
    grid = {}  # grid[(row, col)] = module for snapping reference

    for row in range(1, grid_rows + 1):  # Rows 1-4 (front to back)
        row_name = {1: "Front", 2: "CenterFront", 3: "CenterBack", 4: "Back"}[row]
        App.Console.PrintMessage(f"[Build_950Surf]   === ROW {row} ({row_name.upper()}) ===\n")

        for col in range(1, grid_columns + 1):  # Columns 1-2 (left to right)
            col_name = {1: "Left", 2: "Right"}[col]
            assembly_name = f"Second_Floor_R{row}_C{col}_20x12"

            App.Console.PrintMessage(f"[Build_950Surf]     Creating {assembly_name}...\n")

            # Determine module depth: full joists for rows 1-3, shorter for row 4 (last row)
            is_last_row = (row == grid_rows)
            if is_last_row:
                # Last row uses remaining depth to reach target floor depth
                this_module_depth_in = remaining_depth_in
            else:
                # Full-length rows: don't pass target_module_depth_in (use full joist stock)
                this_module_depth_in = None

            module = parts.create_second_floor_module_20x12(
                doc,
                catalog_rows,
                assembly_name=assembly_name,
                joist_label=SECOND_FLOOR["joist_stock"],
                rim_label=SECOND_FLOOR["rim_stock"],
                make_pressure_treated=SECOND_FLOOR["joist_pressure_treated"],
                hanger_label=SECOND_FLOOR["hanger_label"],
                target_module_width_in=target_module_width_in,
                target_module_depth_in=this_module_depth_in,
            )

            # Position module using snapping
            if row == 1 and col == 1:
                # First module (R1,C1): place at absolute position (anchor for entire floor)
                lc.place_assembly_at(
                    module,
                    x_ft=second_floor_start_x_ft,
                    y_ft=second_floor_start_y_ft,
                    z_ft=second_floor_z_ft
                )
            elif col == 1:
                # First column of subsequent rows: snap to previous row's first column
                prev_module = grid[(row - 1, 1)]
                lc.snap_assembly_corner_to_corner(
                    module, prev_module, target_corner="top_left", assembly_corner="bottom_left"
                )
            else:
                # Column 2: snap to left neighbor in same row
                left_neighbor = grid[(row, col - 1)]
                lc.snap_assembly_corner_to_corner(
                    module, left_neighbor, target_corner="bottom_right", assembly_corner="bottom_left"
                )

            grid[(row, col)] = module
            second_floor_assemblies.append(module)

    # Create Second_Floor_Joists group
    second_floor_joists_grp = bc.create_group(doc, "Second_Floor_Joists")
    bc.add_to_group(second_floor_joists_grp, second_floor_assemblies)

    # Create Second_Floor parent group
    second_floor_parent = bc.create_group(doc, "Second_Floor")
    bc.add_to_group(second_floor_parent, [second_floor_joists_grp])

    App.Console.PrintMessage(
        f"[Build_950Surf]   (done) Created {len(second_floor_assemblies)} second floor modules "
        f"({grid_columns}x{grid_rows} grid = {target_floor_width_ft:.0f}' x {target_floor_depth_ft:.0f}')\n"
    )
    App.Console.PrintMessage("[Build_950Surf] Second floor complete.\n")
else:
    App.Console.PrintMessage("[Build_950Surf] Second floor skipped (disabled in BUILD config)\n")

# ============================================================
# FINAL RECOMPUTE
# ============================================================

App.Console.PrintMessage("[Build_950Surf] Recomputing document...\n")
bc.recompute_once(doc)
App.Console.PrintMessage("[Build_950Surf] Build complete!\n")

# ============================================================
# FINALIZE VIEW (show all, hide helpers, fit camera)
# ============================================================

App.Console.PrintMessage("[Build_950Surf] Finalizing view (show model, hide origins/axes)...\n")

# Show all model objects, hide LCS (Local Coordinate System) helpers
for obj in doc.Objects:
    try:
        type_id = obj.TypeId
        is_helper = (
            type_id == "PartDesign::CoordinateSystem"
            or type_id in ["PartDesign::Plane", "App::Plane", "App::Origin", "App::Line", "App::Axis"]
            or "Axis" in obj.Name
            or "Origin" in obj.Name
        )

        # Set visibility (hide helpers, show everything else)
        if hasattr(obj, "Visibility"):
            obj.Visibility = not is_helper
        if hasattr(obj, "ViewObject") and hasattr(obj.ViewObject, "Visibility"):
            obj.ViewObject.Visibility = not is_helper
    except Exception:
        pass

# Set camera view (if GUI available)
try:
    import FreeCADGui as Gui
    if Gui.ActiveDocument:
        v = Gui.ActiveDocument.ActiveView
        v.setCameraType("Orthographic")
        v.viewIsometric()
        v.fitAll()
        App.Console.PrintMessage("[Build_950Surf] Camera set to isometric and fit.\n")
except Exception:
    pass

# ============================================================
# SAVE DOCUMENT (if path specified via environment)
# ============================================================

save_path = os.environ.get("LUMBER_SAVE_FCSTD")
if save_path:
    try:
        doc.saveAs(save_path)
        App.Console.PrintMessage(f"[Build_950Surf] Saved model to {save_path}\n")
    except Exception as e:
        App.Console.PrintError(f"[Build_950Surf] Failed to save model to {save_path}: {e}\n")
